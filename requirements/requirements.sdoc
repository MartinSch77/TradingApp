[DOCUMENT]
TITLE: TradingApp — Software Requirement Specification (SRS)
UID: SRS-TRADINGAPP

[GRAMMAR]
ELEMENTS:
- TAG: REQUIREMENT
  FIELDS:
  - TITLE: UID
    TYPE: String
    REQUIRED: True
  - TITLE: VERIFICATION
    TYPE: String
    REQUIRED: True
  - TITLE: TITLE
    TYPE: String
    REQUIRED: True
  - TITLE: STATEMENT
    TYPE: String
    REQUIRED: True
  - TITLE: SOURCE
    TYPE: String
    REQUIRED: False
  - TITLE: RATIONALE
    TYPE: String
    REQUIRED: False
  - TITLE: PRIORITY
    TYPE: String
    REQUIRED: False
  - TITLE: STATUS
    TYPE: String
    REQUIRED: False
  - TITLE: ACCEPTANCE_CRITERIA
    TYPE: String
    REQUIRED: False
  - TITLE: ISSUE
    TYPE: String
    REQUIRED: False
  RELATIONS:
  - TYPE: File

[TEXT]
STATEMENT: >>>
This document is the single source of truth for the TradingApp requirements
(requirements-as-code, StrictDoc format). Requirement IDs are stable and
referenced from the design (``docs/design.md``), the test specification
(``docs/test_spec.md``), the test implementations (``tests/tst_*.cpp``, marker
``@relation(REQ-…, scope=function)``) and the generated traceability matrix
(``docs/traceability.html``). ``docs/requirements.md`` is GENERATED from this
file by ``tools/make_requirements.sh`` — do not edit it by hand.

Format: ``REQ-F-xxx`` functional, ``REQ-N-xxx`` non-functional. VERIFICATION:
T = test, A = analysis, I = inspection.
<<<

[[SECTION]]
TITLE: Functional requirements

[REQUIREMENT]
UID: REQ-F-001
VERIFICATION: T
TITLE: Instrument resolution gates trading
STATEMENT: The app shall resolve a user-selected instrument symbol to its eToro instrument id and only enable trading once the resolution is confirmed.

[REQUIREMENT]
UID: REQ-F-002
VERIFICATION: T
TITLE: Live price polling and chart
STATEMENT: The app shall poll live prices for the selected instrument and display them in a chart and price read-out. The chart's price-axis labels and its current-price tag shall carry at least three decimals and shall follow the magnitude of the instrument on screen (more for a low-priced one such as a forex pair), so a label is never rounded to a price the instrument never had.

[REQUIREMENT]
UID: REQ-F-003
VERIFICATION: T
TITLE: Guarded market orders with SL/TP
STATEMENT: The app shall place market orders with a configurable cash amount, leverage, stop-loss and take-profit (entered as account-currency amounts), guarded by a deliberate double-press confirmation.

[REQUIREMENT]
UID: REQ-F-004
VERIFICATION: T
TITLE: Exposure cap and order cooldown
STATEMENT: The app shall reject orders that would exceed a configured total open-exposure cap, and enforce a cooldown between consecutive orders.

[REQUIREMENT]
UID: REQ-F-005
VERIFICATION: T
TITLE: Technical indicators as pure functions
STATEMENT: The app shall compute the classic technical indicators (SMA, EMA, RSI, stochastic %K, MACD histogram, Bollinger %B, volatility, ROC, mean return) as pure functions over a close-price series.

[REQUIREMENT]
UID: REQ-F-006
VERIFICATION: T
TITLE: Statistical forecasts
STATEMENT: The app shall provide statistical forecasts: OLS regression (slope, R²), k-nearest-neighbour analog forecast, Hurst exponent, and a bootstrap Monte-Carlo outlook reporting P(up), a 5–95% range, and the probabilities that a long/short hits take-profit before stop-loss and vice versa.

[REQUIREMENT]
UID: REQ-F-007
VERIFICATION: T
TITLE: Directional signal ensemble
STATEMENT: The app shall combine the indicators into a directional ensemble (BUY / SELL / NEUTRAL with a confidence), and trim the confidence in high-VIX and imminent-event conditions.

[REQUIREMENT]
UID: REQ-F-008
VERIFICATION: T
TITLE: Weighted composite call per instrument
STATEMENT: The app shall blend the available per-instrument sources (technical ensemble, TradingView rating, news sentiment, market regime, crowd sentiment) into a weighted composite call per instrument, renormalising weights over available sources, and rank instruments by confidence.

[REQUIREMENT]
UID: REQ-F-009
VERIFICATION: T
TITLE: Crowd-sentiment tilt (Fear & Greed)
STATEMENT: The app shall obtain crowd sentiment (CNN Fear & Greed, 0–100) and tilt the composite with it: mildly with the crowd for ordinary readings, contrarian at extremes (≤20, ≥80).

[REQUIREMENT]
UID: REQ-F-010
VERIFICATION: T
TITLE: Costed trade plan with risk factor
STATEMENT: 'The app shall build a costed trade plan per instrument: a BUY/SELL/STAY-OUT verdict with reason, Monte-Carlo win/lose probabilities against the proposed barriers, a break-even comparison, a 1–5 risk factor with reasons, and a volatility-targeted leverage recommendation that keeps the loss-at-stop within 25% of the stake, stepped to the instrument''s allowed leverage values and cap. The expected value shall price paths that reach neither barrier at their Monte-Carlo measured mean final move (not a flat-expiry approximation). A BUY/SELL verdict additionally requires ALL of: (a) ensemble confidence of at least 20% after the VIX and event-risk trims, (b) a Monte-Carlo win rate that clears the break-even rate by at least two standard errors of its own estimate (sampling-noise band), and (c) an expected net edge after costs of at least 0.25% of the stake; otherwise the verdict is STAY OUT with the failing gate as the reason.'

[REQUIREMENT]
UID: REQ-F-011
VERIFICATION: T
TITLE: Cost bill: spread, rollover, weekend
STATEMENT: The trade plan's cost bill shall account for half the spread on opening and half on closing, the per-night rollover fee, and the one-off ~3× weekend rollover whenever the holding window includes Friday–Sunday; the expected edge shall be reported net of these costs.

[REQUIREMENT]
UID: REQ-F-012
VERIFICATION: T/I
TITLE: Trade-panel defaults and auto SL/TP
STATEMENT: The trade panel shall default the invest amount to 3750 (display currency) and auto-propose SL/TP from recent volatility (stop ≈ 1.5σ of the horizon move, TP = 1.5 × SL) until the user edits them; an instrument switch re-enables the automatics. The automatic proposal shall never overwrite a stop-loss or take-profit field while it is being edited (keyboard focus inside the field). The same protection applies to the SL/TP cells of the open-trades table: while a cell editor is open, portfolio polls, FX updates and re-prices shall not overwrite that cell's editor; the withheld refresh is applied once editing ends.

[REQUIREMENT]
UID: REQ-F-013
VERIFICATION: T
TITLE: Close watchdog proposes, never executes
STATEMENT: The app shall propose (never execute) closing an open position when the live price leaves the prediction corridor against it or the ensemble flips against it with ≥60% confidence, with a per-position log cooldown.

[REQUIREMENT]
UID: REQ-F-014
VERIFICATION: T
TITLE: Closed-trades lookback with costs
STATEMENT: The app shall list closed trades over a selectable 7–13-week lookback — reachable both from the closed-trades panel and from a button in the main header, and restricted by default to the instruments the app itself trades (with an explicit opt-out that lists the whole account, foreign rows greyed) — with the API's net P/L and rollover fees plus estimated open/close spread costs (half current spread × notional per side) and the spread percentage each estimate priced with, flagging spreads captured while the market was closed (frozen quotes overstate costs); it shall summarise per instrument with a Costs column = spread costs + fees and show the total costs across listed instruments next to the net P/L headline.

[REQUIREMENT]
UID: REQ-F-015
VERIFICATION: T
TITLE: Market-open inference blocks orders
STATEMENT: The app shall infer per-instrument market-open state from whether the instrument's quote timestamp ADVANCES between successive polls — the public rates feed lags real time by minutes, so an absolute quote age must not decide it — and block MARKET orders on closed markets. Where no previous timestamp is known yet (first poll after start), a quote age generous enough to absorb that feed delay shall stand in until the next poll supplies a baseline. Limit orders (REQ-F-027) are exempt from the block: the broker parks them until its market opens, which is the normal way to be positioned for the next session.

[REQUIREMENT]
UID: REQ-F-016
VERIFICATION: T
TITLE: EUR display with live conversion
STATEMENT: The app shall display account figures in EUR using the live EUR/USD rate and convert user inputs back to the account currency for the API.

[REQUIREMENT]
UID: REQ-F-017
VERIFICATION: T
TITLE: Full-featured simulation without credentials
STATEMENT: Without API credentials the app shall run fully functional against a self-contained simulation (synthetic feed, virtual account, closed-trade log).

[REQUIREMENT]
UID: REQ-F-018
VERIFICATION: T
TITLE: Layered configuration
STATEMENT: 'Configuration shall be layered: built-in defaults ← config.json (non-secret) ← apiKeyEtoro.json (secrets, git-ignored) ← environment variables.'

[REQUIREMENT]
UID: REQ-F-019
VERIFICATION: T
TITLE: Independent web reference quote
STATEMENT: The app shall display an independent web reference quote (Yahoo Finance) for the selected instrument with its exchange timestamp and the delta versus the eToro rate.

[REQUIREMENT]
UID: REQ-F-020
VERIFICATION: T
TITLE: Public market-context feeds
STATEMENT: 'The app shall obtain market context from public feeds: CBOE VIX, TradingView technical ratings, per-instrument news headlines, and a macro-economic calendar with per-event impact heuristics.'

[REQUIREMENT]
UID: REQ-F-021
VERIFICATION: I
TITLE: Decision window explains itself in place
STATEMENT: 'The decision window shall explain its conclusions in place: the trade-plan verdict carries a mouse-over stating what the verdict means and why it was reached (incl. the STAY OUT reason), the "expected edge after costs" figure carries a mouse-over defining it with the plan''s own numbers, each ranked-list call carries a mouse-over with its source breakdown, a Trade-plan column shows every ranked instrument''s own plan verdict (BUY/SELL/STAY OUT, computed off the GUI thread with the same cost and break-even gates as the trade-plan panel), a Web signal column shows every ranked instrument''s TradingView multi-timeframe technical rating (the same read that feeds the composite; eToro thematic baskets use the closest liquid ETF/index proxy, n/a where none exists), and an Open column shows each instrument''s live market-open state from the quote-freshness poll.'

[REQUIREMENT]
UID: REQ-F-022
VERIFICATION: T
TITLE: Yahoo intraday momentum as a composite source
STATEMENT: The app shall obtain an independent Yahoo Finance intraday close series (1-minute session bars) per instrument and blend a session-momentum tilt derived from it into the weighted composite call, renormalised with the other sources and shown in the decision window's sources table.

[REQUIREMENT]
UID: REQ-F-023
VERIFICATION: T
TITLE: Event-based activity proposal
STATEMENT: 'For each upcoming calendar event the app shall propose an advisory-only activity: the side (BUY/SELL, from the event class and the forecast-vs-previous change) and the timing — after the print for high-impact events (gap/whipsaw risk), before the release for lower-impact consensus — or STAY OUT with the reason when no direction can be derived. Proposals are never executed automatically.'

[REQUIREMENT]
UID: REQ-F-024
VERIFICATION: I
TITLE: Per-trade gauge window
STATEMENT: 'Clicking the Side cell of an open-trade row shall open a non-modal gauge window for that trade: a dial whose needle is the live price over a stop-loss→open→take-profit scale (loss zone red, win zone green, open-rate marker), plus the buy (open) value, the current value, the live P/L and the SL/TP values; the gauge follows live price ticks of the shown instrument. Clicking the Instrument cell shall instead switch the app to that trade''s instrument (as if picked from the instrument selector); clicks on other cells shall neither open the gauge nor switch the instrument.'

[REQUIREMENT]
UID: REQ-F-025
VERIFICATION: T
TITLE: Open trades mirror the live portfolio
STATEMENT: The open-trades view shall take its position set from the account's live portfolio view, never from cached P/L snapshots, so that a position closed outside the app (in eToro's own UI, or automatically by SL/TP) disappears on the next refresh. Every open trade's P/L shall be marked the way eToro marks it — units × (close rate − open rate) × the instrument's conversion rate, at the bid for a long and the ask for a short — from a quote of the current poll tick for the trade's OWN instrument, not only for the instrument on screen. A quote shall mark a position only while eToro's own timestamp for that price is younger than ~2 minutes: where eToro publishes an instrument's rate behind real time (measured at 6–12 minutes on the .24-7 index variants, and inherited by its /pnl figures), the mark shall come from that instrument's live 1-minute candle close instead, and where no current price exists at all the view shall show eToro's last snapshot figure flagged as not live rather than a figure derived from a stale price. The view shall summarise the open book below the table: the total invested amount — summing the Amount column exactly as it is shown, so the column adds up to the total — and the total P/L, restated on every re-price rather than only per poll, and flagged as not live when any row lacks a current quote. The P/L cell's tooltip shall name the rate its figure is marked at, and the stop-loss and take-profit cells — which show what each leg is worth — shall carry a tooltip naming the instrument RATE that triggers it, its distance from the open rate and from the rate the trade would close at now, the amount the cell states, and whether the stop trails; a leg that is off shall say so rather than read as a trigger at zero. When a position disappears from the portfolio, the app shall refresh the closed-trades list immediately — at most one history walk per 5 s, and the delayed refresh stays armed because the broker's trade history lags the portfolio.

[REQUIREMENT]
UID: REQ-F-026
VERIFICATION: I
TITLE: Manual market-closed override
STATEMENT: 'While the market-open inference reports the selected instrument closed, the app shall offer an explicit "Trade anyway" override that re-enables BUY/SELL, so a wrong closed verdict can never lock the user out of a market that is in fact open. Arming and clearing the override shall be logged, every order placed through it shall be logged as overridden, the double-press confirmation gate shall stay in force, and the override shall clear itself on an instrument switch so it can never carry over to another market.'

[REQUIREMENT]
UID: REQ-F-027
VERIFICATION: T/I
TITLE: Conditional entries are eToro limit orders, not an in-app price watch
STATEMENT: >>>
A conditional entry — "open this trade when the rate reaches X" — shall be placed AT THE BROKER as an eToro limit order (public-API orderType "mit" with a triggerRate), never executed by an in-app price watch: eToro triggers it off its own feed and with the app closed, whereas the app's polled quotes lag the market by minutes and stop entirely when it exits. The order shall carry the trade panel's size, leverage and SL/TP, with the SL/TP amounts converted to rates off the TRIGGER rate (where the position will open), not off the current quote. The app shall list the ACCOUNT's resting limit orders — taken from the broker's own portfolio breakdown, not merely from what this session submitted, so orders placed earlier or in eToro's own UI are visible too — with their live broker status and each order's CURRENT instrument rate (so how far the market still has to travel is visible without switching instruments), allow cancelling one before it executes, report a fill when the broker reports one, and count resting orders against the open-exposure cap. An order on an instrument outside the app's selector shall still be listed (identified by its instrument id), because an order the app hides is an order nobody can cancel. The double-press confirmation gate applies to limit orders as well, and the market-order and limit-order gates shall be independent of one another. Because eToro fills at the trigger rate OR BETTER (lower for a buy, higher for a short), a rate already on the executable side of the market can fill at once instead of resting; the app shall say so in the log before such an order goes out rather than silently letting the user assume it will wait.

A resting order shall be adjustable from that list — trigger rate, stop-loss and take-profit amounts, entered through an editor opened from the order's row — with size, leverage and side carried over unchanged. The public API offers no update-order endpoint, so the app shall implement the change as CANCEL-then-re-place (never the reverse, which could leave two live orders for one intended trade), state in the editor that the order returns under a new id, and place the replacement on the ORDER's own instrument, whichever instrument the app happens to be showing — a limit order is priced off its trigger rate, so it needs no live quote of that instrument (a MARKET order, which must be priced from a live bid/ask, stays restricted to the instrument being traded). Clicking an order's instrument cell shall additionally switch the app to that instrument, the same gesture the open-trades table uses.

A newly placed order shall appear in the list at once, and the list and its per-order statuses shall be refreshed on a fixed 4-second cycle of their own — not on the configurable price-poll cadence — running only while at least one order rests and staying inside the lookup endpoint's shared rate budget. A refresh shall not discard the row the user has marked for cancelling or adjusting. Because an accepted order (HTTP 200 with an order id) can still be REJECTED by the broker seconds later, the app shall additionally re-read a just-placed order's status ahead of that cycle, and shall report a rejection as an error carrying eToro's own reason and error code — an order the app lists as resting must never be one the broker has already refused.
<<<

[REQUIREMENT]
UID: REQ-F-028
VERIFICATION: T/I
TITLE: Scripted trading from a loadable order file
STATEMENT: >>>
The app shall load a plain-text trade script: one order per line, semicolon-separated — `<instrument>; BUY @ <trigger>` or `<instrument>; SELL @ <trigger>` followed by optional keyworded fields in any order: `FROM <yyyy-MM-dd HH:mm>` and `TO <yyyy-MM-dd HH:mm>` (the trading window), `SIGNALS` (trade only on agreement, below), `AMOUNT <stake>`, `SL <amount>`, `TP <amount>`, `TRAILING` (the stop-loss trails), and `LEV <n>`. `#` starts a comment; blank lines are ignored. Loading is all-or-nothing: any unparsable line is reported with its line number and content, and nothing from that file is accepted — a half-loaded script that silently skips lines is how money gets traded that nobody asked for.

Each entry shall be executed as a broker-side eToro limit order through the REQ-F-027 machinery — BUY enters at the trigger rate or LOWER, SELL at the trigger or HIGHER, off the broker's own feed — never by an in-app price watch. An entry's order is placed no earlier than its FROM time (immediately when absent) and cancelled at its TO time if still resting (absent TO = it rests until filled or disarmed). With the SIGNALS flag, the order is placed only while BOTH the technical ensemble and the AI advisor favour the entry's side, is cancelled if either flips while it rests, and may be re-placed if they align again inside the window; an unconfigured AI advisor counts as no recommendation, so flagged entries then never place — the panel shall say so rather than trade on half the evidence. The stop-loss, take-profit and trailing flag carry into the limit order unchanged (amounts, converted off the trigger rate per REQ-F-027). When the requested leverage is not among the instrument's offered values, the app shall use the next LOWER offered value and log the substitution; when the requested value exceeds every offered one, the highest offered value is already that next-lower choice.

Scripted execution is real, unattended trading, so the double-press gate of manual orders is replaced by an equivalent two-step commitment: LOADING a script never places anything, and execution happens only while the user has explicitly ARMED the loaded script — a separate, visible action. Disarming (or loading a different file) shall cancel every scripted order still resting. Each entry executes at most once per arming; every placement, cancellation, substitution and skip shall be logged with the entry's script line; scripted orders count against the open-exposure cap like manual ones. While a script is loaded but DISARMED, the panel shall still evaluate every entry against the live data and log what WOULD be placed — a dry run, so a script can be rehearsed before it is trusted with money.
<<<

[REQUIREMENT]
UID: REQ-F-029
VERIFICATION: T/I
TITLE: Paper-trading bot simulation on live data (simulated money only)
STATEMENT: >>>
The app shall provide an autonomous trading-bot SIMULATION that trades the app's own multi-source decision engine (REQ-F-008) across ALL selectable instruments with SIMULATED money against LIVE market data, so that the question "would this strategy have made money over a longer period" can be answered without risking any. The simulated account shall start at 50 000 EUR (configurable), and the simulation shall be strictly and structurally separated from the broker: the bot shall never place, modify or cancel an order at eToro, never move real money, and never require or use write credentials — it reads quotes, spreads, fees and signals only. Because it therefore moves no money, the double-press gate of REQ-N-005 does not apply to it; it is armed by one explicit visible action instead, and while disarmed it does nothing but keep its books.

Decisions shall come from the same machinery the decision window uses — the weighted composite over the technical ensemble, TradingView rating, news sentiment, VIX/calendar regime, crowd sentiment and the independent intraday series — evaluated for EVERY instrument on each all-instruments scan: a positive composite is a simulated BUY, a negative one a simulated SELL, and the bot shall be deliberately courageous (a low confidence floor) rather than trade rarely, since the purpose is to measure the strategy's behaviour over many trades. An instrument whose market is closed, whose price is unknown or which the bot already holds shall not be entered. Position size, leverage and the stop-loss / take-profit levels shall be derived from the instrument's own recent volatility (the REQ-F-011 geometry: stop ≈ 1.5σ of the horizon, reward:risk 1.5, leverage the largest allowed value keeping the loss at stop within the per-trade risk budget), bounded by a per-trade stake fraction of the CURRENT simulated equity, a total-margin cap and a hard leverage cap.

How MANY trades the bot holds shall not be a policy number: it shall take as many as its decision source judges worthwhile, and the limit shall be a PORTFOLIO RISK BUDGET — the summed loss-if-every-stop-is-hit of all open simulated trades shall stay within a configured fraction of equity, and each new stake shall be clipped to the room that is left. A refusal for that reason shall name it as the risk budget rather than as a queue limit, because the two mean opposite things to whoever reads the log. A concurrency bound may remain only as a sanity limit far above what one-position-per-instrument can reach. Two hard invariants bound the same decision: the simulated account shall never commit more margin than a configured fraction of equity — leaving free margin, since an account with none is one a real broker margin-calls — and it shall NEVER commit money it does not hold: cash, out of which the opening costs are paid on top of the stakes, shall never go negative. An ABSOLUTE ceiling in currency shall additionally bound the committed total, applied on top of the fractional cap with the smaller of the two winning, and switchable off. The two are not redundant and one cannot replace the other: a fraction of CURRENT equity is not a fixed amount of money — thirty percent of fifty thousand is fifteen thousand only while equity is exactly fifty thousand, and it drifts upward after a good week and downward after a bad one — so an instruction of the form "never more than this many euros committed" is inexpressible as a fraction, and expressing it as one would let the bounded quantity move with the very profit and loss it exists to bound. The fractional cap answers a different question, namely that free margin exists whatever the account size. A refusal caused by the absolute ceiling shall be reported as such and NOT as the margin cap, because the two send a reader to change different numbers. The figure the window reports as invested shall be the sum of the individual open positions' own committed amounts, so that adding the visible column up reproduces the total exactly. Each scan shall report both limits (risk at stop against its budget, margin committed against its cap, and free cash), because either can be the one that stopped the bot and the log must not leave the reader guessing which. All computation shall stay off the GUI thread's critical path — the entry evaluation uses closed-form volatility geometry, not the Monte-Carlo path of REQ-F-010.

Simulated fills and costs shall be modelled the way the real path is charged — and each cost charged EXACTLY ONCE, so the measured result is neither flattered nor pessimistic for an invisible reason. Opening and closing shall each cost half the instrument's LIVE spread on the position's notional (REQ-F-025's identity), charged as an explicit, displayed amount; fills and marks shall therefore be priced at the quote's MID, which is economically the ask fill for a buy and the bid fill for a sell once that half-spread is paid, while keeping the transaction cost visible in the books instead of buried inside the rates. Overnight rollover shall be charged per night held from the instrument's own per-unit fees, with the weekend night charged at the tripled rate (REQ-F-013), and a negative fee shall stay a credit. P/L shall use the FX-free identity stake × leverage × (mark − open) / open signed by the side, marked from the same live quotes the real open-trades table is marked from, and a mark taken from a quote that is no longer live shall be shown as such rather than presented as a current P/L. A simulated position shall close when its stop-loss or take-profit rate is touched, when the composite decision flips against it with conviction, or when a maximum holding time expires — each closure recording its reason.

Closing shall also be an ECONOMIC decision, not only a price one, because a leveraged position pays rent every night and eToro bills the Friday night three times (REQ-F-013). Two carry rules shall therefore apply. First, when what is still to be won — the remaining distance to the take-profit on the position's notional — no longer covers what holding it to the end of the intended horizon will cost (the rollover nights in between plus the half-spread it must still cross to exit), the position shall close: a trade that cannot out-earn its own rent is a loss being paid for in instalments. Second, the TRIPLED weekend charge shall have to be earned: a position whose current net does not cover that charge shall be closed before paying it, which also sheds the weekend gap risk, while one already ahead by more than the charge may ride through. A rollover CREDIT shall never be a reason to close — being paid to hold is not a cost — and where the instrument's fee table is unknown the carry rules shall stay silent rather than guess, exactly as the entry gate refuses an unknown spread instead of pricing it at zero. A touched stop or target shall still take precedence over both.

The bot shall be able to take its proposal from a LOCAL large language model instead of (or in addition to) the composite — see REQ-F-030.

The bot's window shall show, at all times: the account line (start capital, cash, invested, equity, open P/L, realised P/L and total P/L in EUR and percent); every OPEN simulated trade with its instrument, side, invested amount, leverage, entry rate, current mark, stop-loss / take-profit, accumulated costs (spread paid to open plus rollover so far) and current P/L; every CLOSED simulated trade with its entry and exit, holding time, total costs, net P/L and WHEN and why it closed — the time of an exit belongs with its reason, since a record of exits without their times says nothing about whether the rules fired when they should; and per-decision log lines stating what the bot did and why it did it. Opening a position shall additionally raise a notice the user acknowledges, so a bot left running cannot open positions unnoticed; that notice shall NOT be modal — a modal box would stop the marking and exit evaluation, freezing the bot until someone clicked — and at most one shall be on screen at a time, because a single scan can open a dozen trades and a dozen stacked dialogs is a lockout rather than a notification. EVERY scan shall additionally log one summary line — candidates considered, trades opened, positions held, risk at stake against the budget, and a count per refusal category — because a window that says nothing while the bot decides nothing is indistinguishable from a broken bot, and the reason a scan opened nothing is exactly what the experimenter needs.

The per-decision lines shall ALSO be appended to a PERSISTENT, human-readable file, one line per instrument the bot considered, stating whether it was traded or not and the reason either way: for a trade, the geometry that was opened beside the evidence that justified it; for a refusal, the stable refusal CODE and the sentence the deciding rule produced. The window's log is held in memory and is lost at the next restart, while this bot is meant to run unattended for weeks — so "why was this instrument never traded on Tuesday?" must be answerable from a file rather than from a log that was discarded. An instrument that was refused is not an omission but the most common outcome, and a file recording only executed trades would explain nothing about the twenty-five instruments the bot examined and left alone. This file is separate from the machine-readable prediction ledger of REQ-F-037 on purpose: the ledger exists to MEASURE decisions, this file exists to be READ, and one format cannot serve both without becoming worse at each.

The simulated books shall survive a restart of the app, and so shall the SESSION state that decides whether the experiment is running at all: the armed flag and the decision-source mode shall be persisted and restored, with the restored state stated in the log. An experiment meant to run for days must not stop silently the first time the app is reopened — an armed bot that comes back disarmed looks exactly like a bot that is working and finding nothing. The books shall be resettable to the starting capital in one action.
<<<

[REQUIREMENT]
UID: REQ-F-030
VERIFICATION: T/I
TITLE: Trading proposal from a local LLM (Ollama) for the simulator
STATEMENT: >>>
The app shall be able to obtain a trading proposal from a LOCAL large language model served by Ollama, and the bot simulation (REQ-F-029) shall be able to trade on it. The model shall be given the SAME evidence prompt the decision window hands the cloud advisor (REQ-F-008) — the ranked candidates with their per-source reads and the market context — and shall answer with a RANKED LIST of proposals — every instrument it considers worth trading now, best first, each with instrument, BUY / SELL / HOLD, a confidence, a leverage and a short rationale — so that the protocol never becomes the thing that limits how many trades the bot takes; that limit is the risk budget of REQ-F-029. A bounded number of picks shall be accepted from one answer, and an empty list ("nothing worth trading") shall be reported as such rather than as a failure or a HOLD. The answer shall be requested as strict JSON (Ollama's `format` field) and parsed defensively: a model that answers with prose, with JSON wrapped in commentary, or with an unknown instrument shall produce a reported failure or a HOLD, never a trade on a guess. A model that runs out of its token budget mid-answer — leaving a valid JSON PREFIX missing its closers, which parses to nothing and wastes the whole turn — shall have the complete picks SALVAGED from that prefix (trim to the last cleanly-closed container, re-balance the braces) rather than discarded; only when not one pick completed is the answer reported as no usable pick. The token budget shall be generous enough that this is the exception, not the rule.

The endpoint and model shall be configuration, not code: an Ollama host (default http://localhost:11434) and a model name, resolvable from config.json and from the environment like every other setting (REQ-F-018), with no key required — this is a local service. The app shall be able to state whether that service is actually usable, by listing the models the daemon serves and reporting a clear diagnosis when the host is unreachable, when no model is configured, or when the configured model is not installed; a missing or unreachable Ollama shall never block the app, the bot, or any other feature.

Because a local model runs on the user's own hardware and may take tens of seconds, the request shall be asynchronous and shall never block the GUI thread, and at most one request shall be in flight at a time. A proposal shall be judged by the AGE of the reasoning behind it, not by whether a newer scan has completed meanwhile: it shall be applied to the latest candidate set while it is younger than one scan cycle — the entry it leads to is re-validated against the live quote, spread and market state of the instrument it names anyway — and shall be dropped, with the delay stated, once it is older than that. Discarding every answer that a newer scan overtook would silently disable the feature on exactly the hardware it exists for, since a slow model is regularly overtaken.

How the simulator uses the proposal shall be an explicit, visible choice with three settings: OFF (the composite decides, as in REQ-F-029), CONFIRM (only the proposal's instrument may be opened, and only while the composite agrees with the model's side — the model is a veto, not a source of direction), and LEAD (the model's own pick and side are traded). In LEAD, a FALLBACK to the composite shall be available and on by default, and it is what lets the bot trade at all on the hardware this feature targets: measured on the bot's own ledger, 442 of 673 refusals were the local model simply not answering while the composite held a direction the whole time. With the fallback on, an instrument on which the model gives no usable answer — no proposal, an unparsable one, or one that named a different instrument — is led by the COMPOSITE direction (every non-model signal: confluence, momentum, the volatility and yield reads, session phase) rather than refused; the model still leads when it speaks. An explicit HOLD from the model is never overridden — a HOLD is an opinion, and trading against it would defeat the mode — and a neutral composite still opens nothing, because the fallback carries a direction, it does not invent one. The set of instruments the bot may trade shall itself be configurable and shall default to the two index CFDs the bot is built to predict (SPX500, NSDQ100); an instrument outside it is refused before any other check with a stable `not-focus` code, and only the focus instruments are put in front of the model. This removes at a stroke the two failure modes the ledger showed: the model spending its one answer on a peripheral name, and the peripheral names (OIL.24-7, USDOLLAR) it led the bot into losing on. In every setting every pick shall be shown and logged with its rationale, so what the model said is on the record whether or not it was acted on, and an instrument refused because the model chose others shall say which ones. In no setting shall the model be able to bypass the risk rules: the stake fraction, the exposure and concurrency caps, the one-position-per-instrument rule, the ruin guard, the market-open and live-spread requirements and the volatility-derived stop/target geometry all continue to apply, and the leverage the model asks for shall be capped by them. The model shall never place a real order — it feeds the simulation only.
<<<

[REQUIREMENT]
UID: REQ-F-031
VERIFICATION: T/A
TITLE: Daily discipline and the evidence gate before real money
STATEMENT: >>>
The bot shall pursue a DAILY result target (default 350 EUR of booked net, configurable) under rules that make the pursuit survivable, and it shall be explicit that no strategy can guarantee a fixed daily profit: the target is a stopping rule, not a promise. Three rules follow from that. Once the day's BOOKED net reaches the target the bot shall open nothing further that day, so a made day cannot be given back; once the day's booked net reaches the loss limit it shall likewise stop opening, so a bad day cannot become a bad month; and in no circumstance shall position size be increased to recover a loss — the stake is a fraction of CURRENT equity, so it can only shrink after losses. Only realised money shall count towards either rule: open profit can still turn, and a rule reading it would stop on nothing. Because a daily goal must therefore be BOOKED, the bot shall close the SMALLEST open position whose own net result — after the exit cost — already completes the day's target, leaving larger winners running; this truncates that one position's upside, which is a deliberate, documented cost of aiming at a daily number rather than at the best possible total, and it shall be switchable. Positions already open shall continue to be governed by their own stops, targets and carry rules. Trading shall be restricted to Monday–Friday, and per instrument to the sessions the market-open inference reports (REQ-F-015).
Both directions shall be traded on equal terms: a negative composite (or a model SELL) shall open a SHORT with mirrored stop/target geometry, the same sizing, the same risk per euro of stake and the sell-side rollover — and the record shall attribute result to longs and shorts separately, so an edge that exists only in a rising market cannot hide inside a total.

Risk shall be aggregated by CORRELATION, not by position count: every instrument shall belong to a bucket of things that move together (equity indices, FX, precious metals, other commodities, crypto; an unrecognised symbol gets its own bucket), the loss-at-stop of the open positions shall be summed per bucket, and no bucket shall be allowed more than a configured fraction of equity — well below the portfolio budget, so that budget cannot be spent on a single market view. Holding a dozen long index positions is one bet with one outcome; the refusal shall name the bucket rather than the portfolio budget, and the scan summary shall show where the risk actually sits.

Where an instrument's real broker constraints differ from an index CFD's, the simulation shall model them rather than assume the index defaults, or it measures a strategy that could not be executed. Crypto (BTC, ETH, SOL, XRP) is the case in point: its leverage shall be capped at the broker's retail crypto ceiling (x2, tighter than the index cap), its cost shall reflect the broker's ~1% round trip rather than an index spread, it shall form its OWN correlation bucket (the majors move together far more than with equities), and — because it trades 24/7 — it shall be EXEMPT from the weekday-only weekend stop that keeps the bot out of the equity weekend gap. A local-model proposal naming an instrument by its exchange pair (BTCUSDT, ETH-USD) shall be mapped onto the broker's own ticker before it is judged, and an instrument shall be reported "not tradable here" only when it is genuinely absent from the catalogue, not merely unscored this cycle. Crypto shall remain a BOT-EXPERIMENT asset class: the manual-trading surfaces — the instrument selector and the screener — shall not offer it, so no crypto order can be armed by hand, while the bot, its evidence views and the correlation buckets keep seeing the full catalogue.

Whether the strategy may be trusted with REAL money shall be decided by measured evidence, never by impression. The app shall compute, from the closed-trade record alone: the number of closed trades and distinct trading days, net after all costs, net per day and the rolling net of the last few days, gross wins and losses, profit factor, expectancy per trade, win rate, the deepest peak-to-trough drawdown of the closed-trade curve in EUR and as a percentage of starting capital, how often the daily target was actually reached, and the long/short split. It shall compare those figures against configurable thresholds — a minimum sample of trades AND of days, a net above zero after costs, a profit factor and an expectancy above stated minima, and a maximum tolerable drawdown — and shall report either readiness or EVERY unmet condition in plain words. The window shall state the verdict and its blockers at all times, so "it seems to work" is never the basis of that decision. Connecting the bot to real-money execution is governed by REQ-F-076, which places that verdict BESIDE the arming control and states it again in the log at the moment of arming — but which, by the owner decision of 2026-09-30 recorded there, does NOT make readiness a precondition of arming: the hard caps, the scope, the kill switch and the double-pressed, time-bounded arming are the safeguards, and the verdict is the evidence the person arming is shown, never a lock.
<<<

[REQUIREMENT]
UID: REQ-F-032
VERIFICATION: T/A
TITLE: The bot manages positions, not just openings
STATEMENT: >>>
The bot shall be able to hold MORE THAN ONE position in the same instrument, but only on the local model's own initiative: a second or further position shall require that the model named that instrument in its current answer, shall be refused beyond a configured count per instrument, and shall be refused beyond a per-instrument share of equity at risk that is tighter than the correlation-bucket cap (several positions in one symbol are the same bet, sized up). Opposite sides in one instrument shall never be held at the same time — a change of side is a close, not a hedge.

The model shall also be asked about what is ALREADY OPEN, not only about what to open next: the evidence prompt shall list the held positions with their side, age and result so far, and a position shall be closed when the model answers with the opposite side for that instrument or asks explicitly to close it. Silence shall NEVER close a position: a small local model regularly answers about a fraction of the instruments it is shown, and reading absence as "close everything" would liquidate the book on a slow answer.

Symmetrically, an ACTIVE keep from the model shall be able to hold a conviction position through carry it has not yet earned — the overnight and, at the weekend, the tripled charge — so that a good opportunity is not surrendered merely because the automatic carry rules would close it before the rent is covered. This override shall be bounded on all three sides that matter: it shall apply ONLY to the economic carry exits (the costs-beat-remaining-edge rule and the unearned-weekend-charge rule) and never to the price stop or target, which are evaluated first and are never waived; the rollover shall still be CHARGED on every mark, so the model holds through the rent rather than escaping it, and the simulation still measures what carrying actually costs; and it shall rest on an ACTIVE keep only, never on silence — the safe default remains to close before an unearned weekend charge, the mirror of the rule that silence never closes. It shall be switchable off, restoring strict carry discipline in which any position that cannot out-earn its own rent is closed. Every open position shall be reviewed on every pass and shall carry the model's CURRENT conclusion where the position is shown — hold, close, or "not mentioned" — with the model's own words as the explanation; "not mentioned" is a first-class state and shall never be displayed as either recommendation. With the model switched off, no such verdict shall be sought or acted on.

Exits shall further follow the trade's own DYNAMICS rather than only its fixed levels. A position whose entry signal has faded to a fraction of the conviction that opened it, and which is not in profit, shall be closed rather than ridden to its stop; a position that was up by a material amount and has handed back most of it shall be closed while it is still a winner. The best result each position has shown shall be remembered across restarts, since that is what the second rule compares against.

Costs shall be part of the ENTRY decision, not only of the exit rules: the gain if the target is reached shall be compared against the full round trip (both half-spreads plus the rollover to the horizon, weekend nights included), and a trade whose target is not worth a configured multiple of what it costs shall be refused with that reason named.
<<<

[REQUIREMENT]
UID: REQ-F-033
VERIFICATION: T/A
TITLE: Learning from the bot's own record
STATEMENT: >>>
Every trade the simulator closes shall be recorded as a training example: the features that were true when it was opened (conviction, volatility, stop and target distance, spread, edge-over-cost, leverage, direction, hour and weekday, and whether the model backed it) together with what the trade actually made after all costs. The record shall be an append-only file, and the label shall be the NET result — a trade that moved the right way but did not cover its costs is a loss and shall be learned as one.

A small feed-forward network shall be trainable from that record by a tool shipped with the project, and the app shall read the resulting model and score each candidate before it is taken. The model's inputs shall be matched BY NAME against the feature list it was trained on, so a model trained on a different set is detected and refused rather than read one column out of step. Validation shall use the LATEST trades in the record, never a random sample, and the measured quality shall be stored with the model.

The network shall have to EARN the right to refuse: below a configured number of training examples, or below a configured out-of-sample quality, it shall be scored and reported but shall never block a trade, and it shall never be able to open one. Its influence shall be configurable between off, advisory and gating, and the window shall state which of those applies together with what the model measured.
<<<

[REQUIREMENT]
UID: REQ-F-034
VERIFICATION: T/A
TITLE: When the bot trades, how often, and what a change of mind costs
STATEMENT: >>>
Trading frequency shall be governed, because every round trip pays two half-spreads and, held overnight, rent: a measured hour of the simulation produced six closes with a median holding time of 5.2 minutes, 1.64 EUR of gross profit and 19.38 EUR of costs — the strategy did not lose that money, the churn did. Three rules shall follow. An instrument whose position has just closed shall not be re-entered for a configured cooldown; the book as a whole shall open no more than a configured number of positions per hour; and no position shall be closed by OPINION — a model changing its mind, a faded signal, a surrendered gain — before it has had a configured minimum time to work. A stop-loss, a take-profit and the carry rules shall remain immediate, because those are prices and economics rather than opinions.

A model's reversal shall additionally have to be CONVINCED: below a configured confidence it shall be reported but not acted on, since a small local model is not consistent between two calls minutes apart and acting on its hesitation costs two half-spreads. Where an opinion exists but may not yet be acted on, the window shall still show it — the minimum holding time is a fact about the trade, not a reason to hide what the model thinks. And it shall have to SAVE something: the reversal shall be acted on only when the position's loss already exceeds a configured multiple of the exit's own cost — the same economics the fade rule applies — because the measured book showed every model exit at the minimum holding time paying a full round-trip spread to abandon a gross-positive position. A refused exit shall be reported with its own countable code; an unknown spread shall keep the guard silent, and stops, targets and the carry rules — prices, not opinions — shall never be affected by it.

Conviction shall only ever be compared with conviction from the SAME source: the composite's confidence at entry shall be recorded separately from whichever number decided the trade, because a model-led entry carries the model's own scale and comparing the two made every such trade appear to have faded the moment it opened.

The trading day's loud windows shall be treated as both opportunity and hazard rather than ignored, each measured on the clock it belongs to — the local exchange for the session edges, New York for the American releases and the central bank — so that the weeks in which Europe and the United States change their clocks on different days need no maintenance and cannot be got wrong by a fixed offset. The windows shall be: the first QUARTER HOUR after an open, which is fast, wide-spread and reverses often enough that it shall be sat out rather than merely sized down (it is also what forms the range whose break is the actual signal); the rest of that first hour, where the opening move becomes readable; the scheduled macro slots (08:30 and 10:00 New York, i.e. 14:30 and 16:00 in Berlin for most of the year); the central-bank window, the statement and the press conference that follows it, which shall likewise be sat out because its first move regularly reverses in full; the last hour before the American close and the final half hour within it. A scheduled release shall take precedence over the "rest of the opening hour" classification, being the more specific fact about that moment. Windows that are not sat out shall require more conviction to enter and shall be traded in smaller size, and both sit-out rules shall be switchable without removing the elevated bar. Named instruments may be treated with RELUCTANCE: the bot shall be allowed to trade them only when the move it expects is both large and fast enough to outrun their costs — the expected move per hour at the chosen leverage, as a percentage of the stake, above a configured floor AND a multiplied conviction floor. The list and both floors shall be configuration, and emptying the list shall remove the reluctance entirely. There are two measured cases, and they fail for OPPOSITE reasons, which is why one mechanism has to cover both. The first is the dollar index: three trades for a net loss, because it moves hundredths of a percent an hour while the spread is indifferent to that — the hourly-move floor is what answers it. The second is CONCENTRATION, and the hourly-move floor cannot see it at all: over one 286-decision run in lead mode the bot opened three positions, two of them the same oil instrument, and that instrument accounted for 179.04 of the 197.05 EUR lost — 91% of the damage from one name that moves perfectly well. The cause is the decision source rather than the instrument: a small local model keeps naming its favourite, so in lead mode one symbol becomes most of the book. The multiplied conviction floor shall therefore apply to such an instrument even when its expected move clears the hourly bar, so that repeating a favourite costs more conviction each time rather than being waved through on volatility alone. Reluctance shall never become a ban: the instrument stays tradable when the evidence is genuinely strong, because a list of forbidden symbols would encode today's model's habits as tomorrow's permanent rule.

The record shall be decomposed BY EXIT RULE — net and count per reason — and presented worst-first, because a total cannot say which rule is losing the money while another is making it; on the first measured 18 closes that decomposition read "signal faded −97.12 over 7" against "banked +99.10 over 2" on a book whose GROSS was positive. A discretionary exit shall additionally have to be worth its own cost: closing a position that is down less than the round trip pays the spread to save nothing.

Leverage shall be bounded per correlation bucket on top of every other cap, with foreign exchange bounded tightest: a few tenths of a percent is a currency pair's whole day, so leverage that merely fits the risk budget can still place the stop inside the noise.

The session's own STRUCTURE shall be read and reported, because it is what a professional looks at before any oscillator and it costs no new data source: where the price sits against the first half hour's range (inside it, or broken up or down, with the excursion measured against the range's own width) and the relative strength of the technology future against the broad-market future — the cheapest available stand-in for market breadth, which would otherwise need per-constituent data this app does not fetch. Both reads shall be put in front of the model as evidence, and the bot shall refuse to open a position INTO a fresh opposite break of that range; where a series is too short for a read, the answer shall be "no read" rather than a fabricated one.

The local model's read shall be shown as a SOURCE wherever the app presents its evidence — in the per-instrument signals panel, in the decision window's source list, and as a hold/close column on the REAL open-trades table, where it is ADVICE: nothing there closes a real position, which stays a human action under REQ-N-005. Its side, its confidence and its own words shall be shown, and three states shall be told apart rather than conflated: "not configured", "shown this instrument and did not pick it", and "not among the instruments it was shown" — the last because the model can only speak about the candidates the prompt listed, and a reader who expects an opinion on every instrument is owed the reason there is none. The number of candidates put in front of the model shall therefore be a parameter of the prompt, and the consumer that reports a per-instrument read shall show it enough instruments to make that read meaningful.

Leverage shall never be a value the instrument does not offer: every ceiling — the account cap, the bucket cap, the instrument's own maximum — shall be applied BEFORE folding to the offered ladder, since clamping an already-folded value to a cap lands on a step nobody sells (an x8 ceiling on an instrument offering 1/2/5/20 must fold to x5).
<<<
SOURCE: Measured from the paper-trading ledger (six closes/hour, 5.2 min median hold, 1.64 EUR gross against 19.38 EUR of costs) plus subsequent live measurements cited inline (the dollar-index and oil-concentration cases).
RATIONALE: Bundled roughly a dozen independently verifiable obligations (churn control, reversal conviction/economics gates, session-phase sit-outs, reluctant-symbol handling, exit-reason reporting, correlation-bucket leverage cap, session-structure reads, model-as-source display, leverage-ladder folding order) under one requirement id. Split into REQ-F-049 through REQ-F-058 (GitHub issue #14, first atomization pass; REQ-F-035 is deferred to a follow-up). Two obligations the split plan flagged as "likely duplicates" of REQ-F-031 and REQ-F-022 were checked against those requirements' own STATEMENTs and found NOT to be duplicates — see REQ-F-055's and REQ-F-056's own RATIONALE for the comparison. This STATEMENT is kept verbatim as the historical record of the bundle; it is no longer the current source of truth for any of its obligations.
PRIORITY: must
STATUS: superseded
ACCEPTANCE_CRITERIA: Superseded by REQ-F-049 (churn control), REQ-F-050 (reversal conviction gate), REQ-F-051 (reversal economics gate), REQ-F-052 (session-phase sit-out windows), REQ-F-053 (reluctant-symbol handling), REQ-F-054 (exit-reason-by-rule reporting), REQ-F-055 (correlation-bucket leverage cap), REQ-F-056 (session-structure reads), REQ-F-057 (local-model-as-source display), REQ-F-058 (leverage-ladder folding order) — each independently traced to its own design element and test, with 0 new hard gaps after the split.
ISSUE: GitHub issue #14 (first pass, REQ-F-034 only); see process/requirements-schema-upgrade.md.

[REQUIREMENT]
UID: REQ-F-049
VERIFICATION: T
TITLE: Churn control — cooldown, pace limit and minimum hold
STATEMENT: >>>
Trading frequency shall be governed, because every round trip pays two half-spreads and, held overnight, rent: a measured hour of the simulation produced six closes with a median holding time of 5.2 minutes, 1.64 EUR of gross profit and 19.38 EUR of costs — the strategy did not lose that money, the churn did. Three rules shall follow. An instrument whose position has just closed shall not be re-entered for a configured cooldown; the book as a whole shall open no more than a configured number of positions per hour; and no position shall be closed by OPINION — a model changing its mind, a faded signal, a surrendered gain — before it has had a configured minimum time to work. A stop-loss, a take-profit and the carry rules shall remain immediate, because those are prices and economics rather than opinions. Each of these rules shall be independently switchable to zero, disabling it without disabling the others, so an experiment can isolate one rule's own contribution to the record.
<<<
SOURCE: Measured from the paper-trading ledger (six closes/hour, 5.2 min median hold, 1.64 EUR gross against 19.38 EUR of costs).
RATIONALE: Split from REQ-F-034 (GitHub issue #14): the churn-control obligation alone — cooldown, pace limit and minimum hold — independent of the reversal conviction/economics gates (REQ-F-050/051) that also police discretionary exits once the minimum hold has elapsed.
PRIORITY: must
STATUS: verified
ACCEPTANCE_CRITERIA: Traced to DES-DOM-WHEN and to TS-PAPER-025, TS-PAPER-026 and TS-PT-035, all passing, with 0 hard gaps.
ISSUE: GitHub issue #14 (REQ-F-034 atomic decomposition, first pass); see process/requirements-schema-upgrade.md.

[REQUIREMENT]
UID: REQ-F-050
VERIFICATION: T
TITLE: Reversal conviction gate, compared on the same scale
STATEMENT: >>>
A model's reversal shall have to be CONVINCED before it is acted on: below a configured confidence it shall be reported but not acted on, since a small local model is not consistent between two calls minutes apart and acting on its hesitation costs two half-spreads. Where an opinion exists but may not yet be acted on, the window shall still show it — the minimum holding time is a fact about the trade, not a reason to hide what the model thinks. A refused exit shall be reported with its own countable code, distinct from the minimum-holding-time refusal, so the two reasons are never conflated in the log. Conviction shall only ever be compared with conviction from the SAME source: the composite's confidence at entry shall be recorded separately from whichever number decided the trade, because a model-led entry carries the model's own scale and comparing the two made every such trade appear to have faded the moment it opened.
<<<
SOURCE: Measured live: in lead mode `entryConfidence` (the model's own scale, ~95) compared directly against the composite's own confidence (~20) closed every AI-led trade on its first mark.
RATIONALE: Split from REQ-F-034 (issue #14): the reversal-conviction gate and the same-source conviction rule are one obligation — the second exists specifically to keep the first from mis-firing when the entry was model-led.
PRIORITY: must
STATUS: verified
ACCEPTANCE_CRITERIA: Traced to DES-DOM-WHEN and TS-PAPER-025, passing, with 0 hard gaps.
ISSUE: GitHub issue #14; see process/requirements-schema-upgrade.md.

[REQUIREMENT]
UID: REQ-F-051
VERIFICATION: T
TITLE: Reversal economics gate — the exit must save more than it costs
STATEMENT: >>>
A model's reversal shall additionally have to SAVE something: it shall be acted on only when the position's loss already exceeds a configured multiple of the exit's own cost — the same economics the fade rule applies — because the measured book showed every model exit at the minimum holding time paying a full round-trip spread to abandon a gross-positive position. A refused exit shall be reported with its own countable code; an unknown spread shall keep the guard silent, and stops, targets and the carry rules — prices, not opinions — shall never be affected by it.
<<<
SOURCE: Measured 2026-08-09: eight crypto closes, gross +149.33 EUR against 478.82 EUR of spread — every "AI says exit" at the 30-minute floor paid a ~60 EUR round trip to abandon a gross-positive position.
RATIONALE: Split from REQ-F-034 (issue #14): distinct from the conviction gate (REQ-F-050) — a confident reversal can still be economically not worth acting on.
PRIORITY: must
STATUS: verified
ACCEPTANCE_CRITERIA: Traced to DES-DOM-WHEN and TS-PAPER-038, passing, with 0 hard gaps.
ISSUE: GitHub issue #14; see process/requirements-schema-upgrade.md.

[REQUIREMENT]
UID: REQ-F-052
VERIFICATION: T
TITLE: Session-phase sit-out and size-down windows
STATEMENT: >>>
The trading day's loud windows shall be treated as both opportunity and hazard rather than ignored, each measured on the clock it belongs to — the local exchange for the session edges, New York for the American releases and the central bank — so that the weeks in which Europe and the United States change their clocks on different days need no maintenance and cannot be got wrong by a fixed offset. The windows shall be: the first QUARTER HOUR after an open, which is fast, wide-spread and reverses often enough that it shall be sat out rather than merely sized down (it is also what forms the range whose break is the actual signal); the rest of that first hour, where the opening move becomes readable; the scheduled macro slots (08:30 and 10:00 New York, i.e. 14:30 and 16:00 in Berlin for most of the year); the central-bank window, the statement and the press conference that follows it, which shall likewise be sat out because its first move regularly reverses in full; the last hour before the American close and the final half hour within it. A scheduled release shall take precedence over the "rest of the opening hour" classification, being the more specific fact about that moment. Windows that are not sat out shall require more conviction to enter and shall be traded in smaller size, and both sit-out rules shall be switchable without removing the elevated bar.
<<<
RATIONALE: Split from REQ-F-034 (issue #14): the session-phase classification, sit-out and size-down obligation alone.
PRIORITY: must
STATUS: verified
ACCEPTANCE_CRITERIA: Traced to DES-DOM-WHEN and TS-PAPER-024, TS-PAPER-026 and TS-PAPER-027, passing, with 0 hard gaps.
ISSUE: GitHub issue #14; see process/requirements-schema-upgrade.md.

[REQUIREMENT]
UID: REQ-F-053
VERIFICATION: T
TITLE: Reluctant-symbol handling — a floor on the move and a floor on conviction
STATEMENT: >>>
Named instruments may be treated with RELUCTANCE: the bot shall be allowed to trade them only when the move it expects is both large and fast enough to outrun their costs — the expected move per hour at the chosen leverage, as a percentage of the stake, above a configured floor AND a multiplied conviction floor. The list and both floors shall be configuration, and emptying the list shall remove the reluctance entirely. There are two measured cases, and they fail for OPPOSITE reasons, which is why one mechanism has to cover both. The first is the dollar index: three trades for a net loss, because it moves hundredths of a percent an hour while the spread is indifferent to that — the hourly-move floor is what answers it. The second is CONCENTRATION, and the hourly-move floor cannot see it at all: over one 286-decision run in lead mode the bot opened three positions, two of them the same oil instrument, and that instrument accounted for 179.04 of the 197.05 EUR lost — 91% of the damage from one name that moves perfectly well. The multiplied conviction floor shall therefore apply to such an instrument even when its expected move clears the hourly bar, so that repeating a favourite costs more conviction each time rather than being waved through on volatility alone. Reluctance shall never become a ban: the instrument stays tradable when the evidence is genuinely strong, because a list of forbidden symbols would encode today's model's habits as tomorrow's permanent rule. The same reluctance bar shall additionally apply to any instrument outside a configured CORE focus set, refused as peripheral rather than individually named, so that widening the traded universe cannot let peripheral names dominate the book the way six of them once took 81% of a measured loss.
<<<
SOURCE: Measured: 3 USDOLLAR trades for -19.22 EUR; a 286-decision lead-mode run in which OIL.24-7 alone carried -179.04 of -197.05 EUR net; 2026-08-11, six peripheral names took 8 of 19 closed trades for -256 EUR of a -316 EUR book (81%).
RATIONALE: Split from REQ-F-034 (issue #14). The peripheral-symbol variant (`coreFocusSymbols`) postdates the original STATEMENT but is the SAME mechanism applied to a second trigger (outside-core rather than individually named) — verified by TS-PAPER-039 alongside TS-PAPER-029/030, so it is folded into this same obligation rather than split out.
PRIORITY: must
STATUS: verified
ACCEPTANCE_CRITERIA: Traced to DES-DOM-WHEN and TS-PAPER-029, TS-PAPER-030 and TS-PAPER-039, passing, with 0 hard gaps.
ISSUE: GitHub issue #14; see process/requirements-schema-upgrade.md.

[REQUIREMENT]
UID: REQ-F-054
VERIFICATION: T
TITLE: Exit record decomposed by rule, and a floor on discretionary exits
STATEMENT: >>>
The record shall be decomposed BY EXIT RULE — net and count per reason — and presented worst-first, because a total cannot say which rule is losing the money while another is making it; on the first measured 18 closes that decomposition read "signal faded" -97.12 over 7 trades against "banked before giving it back" +99.10 over 2, on a book whose GROSS was positive. A discretionary exit shall additionally have to be worth its own cost: closing a position that is down less than the round trip pays the spread to save nothing, so a discretionary rule such as the fade exit shall act only once the loss exceeds a configured multiple of the exit's own cost.
<<<
SOURCE: Measured: first 18 real closes, "signal faded" -97.12 EUR over 7 trades vs "banked before giving it back" +99.10 EUR over 2 trades, on a book whose gross was +119.35 against 148.77 EUR of costs.
RATIONALE: Split from REQ-F-034 (issue #14): the reporting decomposition and the discretionary-exit cost floor are one paragraph's obligation in the original bundled STATEMENT and stay together here.
PRIORITY: must
STATUS: verified
ACCEPTANCE_CRITERIA: Traced to DES-DOM-WHEN and TS-PAPER-028, passing, with 0 hard gaps.
ISSUE: GitHub issue #14; see process/requirements-schema-upgrade.md.

[REQUIREMENT]
UID: REQ-F-055
VERIFICATION: T
TITLE: Leverage bounded per correlation bucket, foreign exchange tightest
STATEMENT: >>>
Leverage shall be bounded per correlation bucket on top of every other cap, with foreign exchange bounded tightest: a few tenths of a percent is a currency pair's whole day, so leverage that merely fits the risk budget can still place the stop inside the noise. Every recognised bucket, and any symbol the catalogue does not recognise, shall have a reachable ceiling of its own.
<<<
RATIONALE: Split from REQ-F-034 (issue #14). The split plan flagged this as "likely a duplicate" of REQ-F-031's own correlation-bucket rule; checked directly against REQ-F-031's STATEMENT and found NOT to be a duplicate. REQ-F-031 bounds the SUMMED loss-at-stop per bucket (`maxGroupRiskFraction`, an aggregate risk cap) — its STATEMENT never mentions leverage. This requirement bounds the LEVERAGE offered per bucket (`groupLeverageCap`) — a different ceiling that happens to share the same `correlationGroup` taxonomy as REQ-F-031's risk cap, and is enforced in the same source file (`PaperTrader.cpp`) but by a separate function.
PRIORITY: must
STATUS: verified
ACCEPTANCE_CRITERIA: Traced to DES-DOM-WHEN and TS-PAPER-025 and TS-PAPER-027, passing, with 0 hard gaps.
ISSUE: GitHub issue #14; see process/requirements-schema-upgrade.md.

[REQUIREMENT]
UID: REQ-F-056
VERIFICATION: T
TITLE: Session-structure reads — opening range and relative strength
STATEMENT: >>>
The session's own STRUCTURE shall be read and reported, because it is what a professional looks at before any oscillator and it costs no new data source: where the price sits against the first half hour's range (inside it, or broken up or down, with the excursion measured against the range's own width) and the relative strength of the technology future against the broad-market future — the cheapest available stand-in for market breadth, which would otherwise need per-constituent data this app does not fetch. Both reads shall be put in front of the model as evidence, and the bot shall refuse to open a position INTO a fresh opposite break of that range; where a series is too short for a read, the answer shall be "no read" rather than a fabricated one.
<<<
RATIONALE: Split from REQ-F-034 (issue #14). The split plan flagged this as "likely a duplicate" of REQ-F-022; checked directly against REQ-F-022's STATEMENT and found NOT to be a duplicate. REQ-F-022 blends a session-momentum TILT derived from the Yahoo intraday series into the weighted composite call. This requirement is a SEPARATE evidence read (opening-range position, futures relative strength) shown to the model on its own and additionally enforced as a hard entry refusal (`against-range-break`) — a different mechanism, built on the same 1-minute series REQ-F-022 also uses, but not the same obligation.
PRIORITY: must
STATUS: verified
ACCEPTANCE_CRITERIA: Traced to DES-DOM-WHEN and TS-PAPER-026, passing, with 0 hard gaps.
ISSUE: GitHub issue #14; see process/requirements-schema-upgrade.md.

[REQUIREMENT]
UID: REQ-F-057
VERIFICATION: T/A
TITLE: The local model's read shown as a source, on the real open-trades table
STATEMENT: >>>
The local model's read shall be shown as a SOURCE wherever the app presents its evidence — in the per-instrument signals panel, in the decision window's source list, and as a hold/close column on the REAL open-trades table, where it is ADVICE: nothing there closes a real position, which stays a human action under REQ-N-005. Its side, its confidence and its own words shall be shown, and three states shall be told apart rather than conflated: "not configured", "shown this instrument and did not pick it", and "not among the instruments it was shown" — the last because the model can only speak about the candidates the prompt listed, and a reader who expects an opinion on every instrument is owed the reason there is none. The number of candidates put in front of the model shall therefore be a parameter of the prompt, and the consumer that reports a per-instrument read shall show it enough instruments to make that read meaningful.
<<<
RATIONALE: Split from REQ-F-034 (issue #14). Checked against REQ-F-030 and found NOT to be a duplicate: REQ-F-030 governs OBTAINING a proposal for the SIMULATOR; this governs DISPLAYING the model's read as advice on the REAL (not simulated) open-trades table — already reflected independently in DES-UI-POSMODEL's own `satisfies` column (`PositionsModel::setAiOpinions`/`ColAi`). At the split no test carried a tag for this obligation specifically, and it was left as an open (non-hard) coverage gap rather than mistagged onto a test that does not exercise it; TS-PM-006 (added 2026-09-29) is that dedicated test.
PRIORITY: must
STATUS: verified
ACCEPTANCE_CRITERIA: Traced to DES-UI-POSMODEL and TS-PM-006, passing, with 0 hard gaps: the open-trades table's AI column shows hold/close/"—" with the model's own words, still shows a close it may not act on yet, refreshes one column without a reset, and is read-only — no edit, no signal and no row removal can come from it.
ISSUE: GitHub issue #14; see process/requirements-schema-upgrade.md.

[REQUIREMENT]
UID: REQ-F-058
VERIFICATION: T
TITLE: Leverage caps apply before folding to the offered ladder
STATEMENT: >>>
Leverage shall never be a value the instrument does not offer: every ceiling — the account cap, the bucket cap, the instrument's own maximum — shall be applied BEFORE folding to the offered ladder, since clamping an already-folded value to a cap lands on a step nobody sells (an x8 ceiling on an instrument offering 1/2/5/20 must fold to x5).
<<<
RATIONALE: Split from REQ-F-034 (issue #14): the fold-order obligation alone, independent of which cap (account, bucket or instrument) turns out to be tightest.
PRIORITY: must
STATUS: verified
ACCEPTANCE_CRITERIA: Traced to DES-DOM-WHEN and TS-PAPER-025 and TS-PAPER-027, passing, with 0 hard gaps.
ISSUE: GitHub issue #14; see process/requirements-schema-upgrade.md.

[REQUIREMENT]
UID: REQ-F-035
VERIFICATION: T/A
TITLE: Independent reads, and agreement between them
STATEMENT: >>>
Prediction shall rest on AGREEMENT BETWEEN INDEPENDENT reads rather than on a stack of indicators derived from the same closes: an oscillator, a moving-average cross and a momentum study computed from one price series are one piece of evidence wearing three hats. The app shall therefore fetch and report reads that are independent of its own price history, each from a source it can actually obtain: the futures that lead the cash market (the Nasdaq future against the S&P future, i.e. whether technology is carrying the move or lagging it), that same future's own push read over SEVERAL horizons at once (one read, not three — a 1-, 5- and 15-minute return computed from one series are one piece of evidence wearing three hats, so what counts is whether they AGREE, and horizons that disagree shall be reported as the neutral they describe), expected volatility read by its DIRECTION rather than its level (the Nasdaq-specific index for a Nasdaq instrument, the broad one otherwise), the US 10-year yield whose rises press on growth shares, the SHAPE of the curve as the short end against the long end (the policy read, which regularly disagrees with the level of long rates and matters most to a technology index; the read shall name which front-end instrument it actually obtained), how many of the index's heavyweight constituents are actually participating, how many of them trade above their OWN session VWAP, whether the session's VOLUME sits behind the rising names or the falling ones, and where price sits against its own opening range.

The two volume reads are what separate "the names are up" from "the names are being bought", and they require volume bars whose closes and volumes are ALIGNED bar for bar: a close series and a volume series parsed independently skip different empty minutes, and a VWAP computed across that shift is a number about nothing. Where a feed carries no volume — the volatility and yield indices do not — both reads shall be UNKNOWN rather than zero.

The volatility TERM STRUCTURE (the near leg against the far leg) shall additionally be reported, and shall never be counted as a direction: an inverted curve says the market is paying up for protection right now, which is a statement about how much the next print can overrule and not about which way it goes. It shall therefore only ever REDUCE conviction, exactly as an elevated level does.

The reads shall be supplied from books that are keyed the way their sources are keyed, and a read shall never search the wrong one: the reference tickers are keyed by TICKER and the futures proxies by the app's own INSTRUMENT SYMBOL, and mixing them silently disables a read while leaving every test that mixes them in the same way green. The constituent list shall be the one belonging to THAT index — up to ten names by weight, the Nasdaq-100's for a Nasdaq instrument and the S&P 500's otherwise — because the two lists agree at the top and differ exactly in the tail that distinguishes the indices, and reading the wrong tail reads a different market. The read shall name which list it counted.

For each read the app shall report the direction it supports, the number behind it, and — decisively — whether it could be MEASURED AT ALL. A read whose series is missing shall be UNKNOWN and shall never count as agreement: a confluence of "four conditions met" must mean four measured conditions rather than four absent feeds. Heavyweight participation shall be named as a STAND-IN for market breadth wherever it appears, because true breadth (the advance/decline line, up-volume, the share of constituents above their session average) needs per-constituent data this app does not fetch, and a stand-in presented as the real thing is worse than an honest gap.

The constituents shall additionally be shown IN THEIR OWN VIEW as an early read on the two indices: the ten names of each index side by side with their session moves, how many of them are up, the average move of the readable ones, and which single name is leading and which is lagging — because an index carried by one name and an index carried by all ten are different situations that the same index price cannot tell apart. That view shall state, on screen rather than in a comment, that it is a STAND-IN for market breadth, and a constituent whose price could not be read shall be shown as UNKNOWN rather than as a zero move.

Beside the equal-weight average, the app shall report a single SUMMARISED direction for the top constituents together — a CAP-WEIGHTED move, each name scaled by its share of the index and renormalised over the readable names — as the "in which direction are the top names pulling the index, up or down" indicator, because the index itself is cap-weighted and a large name moving is not a small name moving, and the top names can carry the index against the majority count (the index lagging its heaviest constituents is exactly the situation this is meant to surface). Direction shall be carried by a sign and a shape, never by colour alone. The weights used shall be an APPROXIMATE STATIC snapshot — this app does not fetch live index weightings — and shall be labelled as such on the same footing as the breadth stand-in caveat — enough to weight the heaviest name above the lightest by roughly the right ratio, never a claim to the index's exact construction.

The count of agreeing reads shall be shown per instrument alongside the app's other signals, shall be given to the model as evidence in those words, and shall gate the bot: an index position shall not be opened while fewer than a configured number of the MEASURED reads agree with its side. That threshold shall be configurable, shall be satisfiable (never more than the number of reads actually available), and shall be able to be switched off — with the reads still shown and still given to the model, because a read nobody acts on is still information a reader is owed.
<<<
SOURCE: Design decision (REQ-F-035 predates this schema); the majority-agreement floor is additionally grounded in the measured regression TS-PAPER-025 documents (an absolute floor of 3 silently weakened as reads were added).
RATIONALE: Bundled the nine independent reads, the rules they are measured, keyed and counted under, the volatility term structure, the agreement gate and two DISPLAY-only work products (the constituent own-view, the cap-weighted lead indicator) under one requirement id. Split into REQ-F-059 through REQ-F-075 (GitHub issue #14, second and final atomization pass): one requirement per read (REQ-F-059 to REQ-F-067), one for the agreement count and gate (REQ-F-069), one per display (REQ-F-074, REQ-F-075), and — decided obligation by obligation and recorded in each successor's own RATIONALE — five cross-cutting obligations given ids of their own because each constrains several reads, or a layer below them, rather than one read: measurability (REQ-F-068), book keying (REQ-F-070), the per-index constituent list (REQ-F-071), aligned volume bars (REQ-F-072) and the volatility term structure (REQ-F-073). The heavyweight-participation STAND-IN rule stays with the participation read (REQ-F-064), and the "one read, not three" horizon rule with the futures-push read (REQ-F-060). Suspected duplicates were checked against the other requirements' own STATEMENTs rather than assumed: the opening-range read is NOT a duplicate of REQ-F-022 and only PARTLY one of REQ-F-056 (see REQ-F-067), the futures-leadership read shares its measurement with REQ-F-056 but not its obligation (REQ-F-059), and neither display duplicates REQ-F-036 or REQ-F-038 (REQ-F-074, REQ-F-075). This STATEMENT is kept verbatim as the historical record of the bundle; it is no longer the current source of truth for any of its obligations.
PRIORITY: must
STATUS: superseded
ACCEPTANCE_CRITERIA: Superseded by REQ-F-059 (futures-leadership read), REQ-F-060 (futures-push read), REQ-F-061 (volatility-direction read), REQ-F-062 (10-year yield read), REQ-F-063 (curve-shape read), REQ-F-064 (heavyweight-participation read), REQ-F-065 (above-own-VWAP read), REQ-F-066 (up/down-volume read), REQ-F-067 (opening-range position read), REQ-F-068 (measurability — UNKNOWN never counts as agreement), REQ-F-069 (agreement count and gate), REQ-F-070 (read inputs keyed as their sources are keyed), REQ-F-071 (per-index constituent list), REQ-F-072 (aligned volume bars), REQ-F-073 (volatility term structure), REQ-F-074 (constituent own view), REQ-F-075 (cap-weighted constituent lead) — each independently traced to its own design element and test, with 0 new hard gaps after the split.
ISSUE: GitHub issue #14 (second pass, REQ-F-035); see process/requirements-schema-upgrade.md.

[REQUIREMENT]
UID: REQ-F-059
VERIFICATION: T
TITLE: Futures-leadership read — the Nasdaq future against the S&P future
STATEMENT: >>>
As one of the independent reads of REQ-F-069, the app shall fetch and report the futures that lead the cash market: the Nasdaq future against the S&P future, i.e. whether technology is carrying the move or lagging it. Like every read, it shall report the direction it supports, the number behind it and whether it could be measured at all (REQ-F-068).
<<<
SOURCE: Design decision carried over from REQ-F-035 (which predates the SOURCE field).
RATIONALE: Split from REQ-F-035 (GitHub issue #14, second pass): the first of the nine independent reads. Checked against REQ-F-056, whose STATEMENT also reads "the relative strength of the technology future against the broad-market future" and which is computed by the SAME `relativeStrength` function over the same two futures series: the MEASUREMENT is shared, so it is not re-specified here, but the requirement is NOT a duplicate — REQ-F-056 obliges that reading to be put in front of the model as evidence, while this one obliges it to be one of the COUNTED independent reads (a vote in `confluenceFor`, under REQ-F-068's UNKNOWN rule and read from the symbol book REQ-F-070 requires). Removing either would lose an obligation the other does not carry.
PRIORITY: must
STATUS: verified
ACCEPTANCE_CRITERIA: Traced to DES-DOM-CONFLUENCE and TS-CONF-002, TS-CONF-006 and TS-DEC-010, passing, with 0 hard gaps.
ISSUE: GitHub issue #14 (REQ-F-035 atomic decomposition, second pass); see process/requirements-schema-upgrade.md.

[REQUIREMENT]
UID: REQ-F-060
VERIFICATION: T
TITLE: Futures-push read — several horizons, counted as ONE read
STATEMENT: >>>
As one of the independent reads of REQ-F-069, the app shall fetch and report the leading future's own push, read over SEVERAL horizons at once — one read, not three: a 1-, 5- and 15-minute return computed from one series are one piece of evidence wearing three hats, so what counts is whether they AGREE, and horizons that disagree shall be reported as the neutral they describe. Like every read, it shall report the direction it supports, the number behind it and whether it could be measured at all (REQ-F-068).
<<<
SOURCE: Design decision carried over from REQ-F-035 (which predates the SOURCE field).
RATIONALE: Split from REQ-F-035 (issue #14, second pass). Kept apart from the futures-leadership read (REQ-F-059) although both read the futures: leadership compares two futures with each other, the push reads one future against its own recent past, and the two can disagree. The "one read, not three" rule stays HERE rather than in the agreement count (REQ-F-069), because it is this read's own definition that stops three horizons of one series from being counted as three votes.
PRIORITY: must
STATUS: verified
ACCEPTANCE_CRITERIA: Traced to DES-DOM-CONFLUENCE and TS-CONF-006, passing, with 0 hard gaps.
ISSUE: GitHub issue #14 (REQ-F-035 atomic decomposition, second pass); see process/requirements-schema-upgrade.md.

[REQUIREMENT]
UID: REQ-F-061
VERIFICATION: T
TITLE: Volatility-direction read — the index's own volatility index, by direction
STATEMENT: >>>
As one of the independent reads of REQ-F-069, the app shall fetch and report expected volatility read by its DIRECTION rather than its level — the Nasdaq-specific volatility index for a Nasdaq instrument, the broad one otherwise. Like every read, it shall report the direction it supports, the number behind it and whether it could be measured at all (REQ-F-068).
<<<
SOURCE: Design decision carried over from REQ-F-035 (which predates the SOURCE field).
RATIONALE: Split from REQ-F-035 (issue #14, second pass). Distinct from the volatility TERM STRUCTURE (REQ-F-073), which REQ-F-035 reports beside it but never counts as a direction, and from REQ-F-036's regime input, where the LEVEL of expected volatility may only reduce the combined indication — this read counts the DIRECTION as a vote.
PRIORITY: must
STATUS: verified
ACCEPTANCE_CRITERIA: Traced to DES-DOM-CONFLUENCE and TS-CONF-001 and TS-CONF-002, passing, with 0 hard gaps.
ISSUE: GitHub issue #14 (REQ-F-035 atomic decomposition, second pass); see process/requirements-schema-upgrade.md.

[REQUIREMENT]
UID: REQ-F-062
VERIFICATION: T
TITLE: US 10-year yield read
STATEMENT: >>>
As one of the independent reads of REQ-F-069, the app shall fetch and report the US 10-year yield, whose rises press on growth shares. Like every read, it shall report the direction it supports, the number behind it and whether it could be measured at all (REQ-F-068).
<<<
SOURCE: Design decision carried over from REQ-F-035 (which predates the SOURCE field).
RATIONALE: Split from REQ-F-035 (issue #14, second pass): the LEVEL-of-long-rates read, kept apart from the curve-shape read (REQ-F-063) because REQ-F-035 itself says the two regularly disagree — which is what makes both worth counting.
PRIORITY: must
STATUS: verified
ACCEPTANCE_CRITERIA: Traced to DES-DOM-CONFLUENCE and TS-CONF-001 and TS-CONF-002, passing, with 0 hard gaps.
ISSUE: GitHub issue #14 (REQ-F-035 atomic decomposition, second pass); see process/requirements-schema-upgrade.md.

[REQUIREMENT]
UID: REQ-F-063
VERIFICATION: T
TITLE: Curve-shape read — short end against long end, naming its front-end source
STATEMENT: >>>
As one of the independent reads of REQ-F-069, the app shall fetch and report the SHAPE of the yield curve as the short end against the long end — the policy read, which regularly disagrees with the level of long rates and matters most to a technology index. The read shall name which front-end instrument it actually obtained. Like every read, it shall report the direction it supports, the number behind it and whether it could be measured at all (REQ-F-068).
<<<
SOURCE: Design decision carried over from REQ-F-035 (which predates the SOURCE field).
RATIONALE: Split from REQ-F-035 (issue #14, second pass). The "name which front-end instrument it obtained" clause belongs to this read alone: it is the only read with a fallback source (the 2-year yield future, else the 13-week bill), and a read whose source is ambiguous cannot be audited.
PRIORITY: must
STATUS: verified
ACCEPTANCE_CRITERIA: Traced to DES-DOM-CONFLUENCE and TS-CONF-001 and TS-CONF-006, passing, with 0 hard gaps.
ISSUE: GitHub issue #14 (REQ-F-035 atomic decomposition, second pass); see process/requirements-schema-upgrade.md.

[REQUIREMENT]
UID: REQ-F-064
VERIFICATION: T
TITLE: Heavyweight-participation read, named as a stand-in for breadth
STATEMENT: >>>
As one of the independent reads of REQ-F-069, the app shall fetch and report how many of the index's heavyweight constituents (REQ-F-071) are actually participating. Heavyweight participation shall be named as a STAND-IN for market breadth wherever it appears, because true breadth (the advance/decline line, up-volume, the share of constituents above their session average) needs per-constituent data this app does not fetch, and a stand-in presented as the real thing is worse than an honest gap. Like every read, it shall report the direction it supports, the number behind it and whether it could be measured at all (REQ-F-068).
<<<
SOURCE: Design decision carried over from REQ-F-035 (which predates the SOURCE field); the constituent feed's measured regression of 2026-08-07 (a barless Yahoo equity response left every constituent unread, the read dark and nothing saying so) is pinned by TS-FEED-014.
RATIONALE: Split from REQ-F-035 (issue #14, second pass). The STAND-IN naming rule is kept HERE rather than made a requirement of its own because REQ-F-035 states it of this read specifically; the constituent view carries its own on-screen stand-in clause (REQ-F-074). At the split (2026-09-29) STATUS was `approved`, not `implemented`: the read itself was implemented and verified (TS-CONF-002: support for a broadly-up field, measured-neutral for a split one, UNKNOWN for a field too thin to read, the index's own list named; TS-FEED-014: a constituent's session change stays measurable from a barless response), but the read's own detail text — what reaches the model's evidence (`confluenceLine`) and the cockpit meter's tick detail — carried no stand-in label. It now reads "8 of 10 Nasdaq-100 heavyweights up (stand-in for breadth)", the same wording the above-VWAP read already used, and TS-CONF-002 pins it.
PRIORITY: must
STATUS: verified
ACCEPTANCE_CRITERIA: Traced to DES-DOM-CONFLUENCE and TS-CONF-002 and TS-FEED-014, passing, with 0 hard gaps: the participation read's own detail text names it a stand-in for breadth (TS-CONF-002), as do the signals-panel tooltip and the Heavyweights window.
ISSUE: GitHub issue #14 (REQ-F-035 atomic decomposition, second pass); see process/requirements-schema-upgrade.md.

[REQUIREMENT]
UID: REQ-F-065
VERIFICATION: T
TITLE: Heavyweights above their own session VWAP
STATEMENT: >>>
As one of the independent reads of REQ-F-069, the app shall fetch and report how many of the index's heavyweight constituents (REQ-F-071) trade above their OWN session VWAP. It is one of the two volume reads and rests on the aligned volume bars of REQ-F-072, being UNKNOWN rather than zero where a feed carries no volume. Like every read, it shall report the direction it supports, the number behind it and whether it could be measured at all (REQ-F-068).
<<<
SOURCE: Design decision carried over from REQ-F-035 (which predates the SOURCE field).
RATIONALE: Split from REQ-F-035 (issue #14, second pass): the split plan's "breadth-by-VWAP" read. Its data prerequisite — closes and volumes aligned bar for bar, UNKNOWN without volume — is shared with the up/down-volume read and is therefore its own requirement (REQ-F-072) rather than restated in both.
PRIORITY: must
STATUS: verified
ACCEPTANCE_CRITERIA: Traced to DES-DOM-CONFLUENCE and TS-CONF-005, passing, with 0 hard gaps.
ISSUE: GitHub issue #14 (REQ-F-035 atomic decomposition, second pass); see process/requirements-schema-upgrade.md.

[REQUIREMENT]
UID: REQ-F-066
VERIFICATION: T
TITLE: Up/down-volume read — is the volume behind the rising names or the falling ones
STATEMENT: >>>
As one of the independent reads of REQ-F-069, the app shall fetch and report whether the session's VOLUME sits behind the rising heavyweight names or the falling ones, over the index's own constituents (REQ-F-071). It is one of the two volume reads and rests on the aligned volume bars of REQ-F-072, being UNKNOWN rather than zero where a feed carries no volume. Like every read, it shall report the direction it supports, the number behind it and whether it could be measured at all (REQ-F-068).
<<<
SOURCE: Design decision carried over from REQ-F-035 (which predates the SOURCE field).
RATIONALE: Split from REQ-F-035 (issue #14, second pass). The split plan's working name for this read, "volume-delta", is deliberately NOT used: volume delta proper (buy- minus sell-initiated volume, cumulative delta, bid/ask imbalance) is order flow, which needs level-2 data this app does not have. What REQ-F-035 actually states is the up/down split of session volume across the heavyweights, and naming it after the real measure would be exactly the stand-in-presented-as-the-real-thing REQ-F-064 forbids.
PRIORITY: must
STATUS: verified
ACCEPTANCE_CRITERIA: Traced to DES-DOM-CONFLUENCE and TS-CONF-005, passing, with 0 hard gaps.
ISSUE: GitHub issue #14 (REQ-F-035 atomic decomposition, second pass); see process/requirements-schema-upgrade.md.

[REQUIREMENT]
UID: REQ-F-067
VERIFICATION: T
TITLE: Opening-range position as a counted read
STATEMENT: >>>
As one of the independent reads of REQ-F-069, the app shall report where price sits against its own opening range. Like every read, it shall report the direction it supports, the number behind it and whether it could be measured at all (REQ-F-068).
<<<
SOURCE: Design decision carried over from REQ-F-035 (which predates the SOURCE field).
RATIONALE: Split from REQ-F-035 (issue #14, second pass). Both suspected duplicates were checked against their actual STATEMENTs. REQ-F-022: NOT a duplicate — it blends a session-momentum TILT from the intraday series into the weighted composite and says nothing about an opening range. REQ-F-056: PARTLY a duplicate — it already obliges reading and reporting where price sits against the first half hour's range (inside it or broken up/down, the excursion against the range's own width, "no read" when the series is too short), and both are computed by the same `openingRange` function, so that reading is NOT re-specified here. What REQ-F-056 does not oblige, and this requirement alone does, is that the reading is one of the independent reads COUNTED for agreement — a vote in `confluenceFor`, UNKNOWN when unmeasurable and then never agreement — whereas REQ-F-056's consumers are the model's evidence and the `against-range-break` refusal. The obligation therefore stays, narrowed to that role.
PRIORITY: must
STATUS: verified
ACCEPTANCE_CRITERIA: Traced to DES-DOM-CONFLUENCE and TS-CONF-002, passing, with 0 hard gaps.
ISSUE: GitHub issue #14 (REQ-F-035 atomic decomposition, second pass); see process/requirements-schema-upgrade.md.

[REQUIREMENT]
UID: REQ-F-068
VERIFICATION: T
TITLE: Every read states whether it was measured — UNKNOWN never counts as agreement
STATEMENT: >>>
For each independent read the app shall report the direction it supports, the number behind it, and — decisively — whether it could be MEASURED AT ALL. A read whose series is missing shall be UNKNOWN and shall never count as agreement: a confluence of "four conditions met" must mean four measured conditions rather than four absent feeds.
<<<
SOURCE: Design decision carried over from REQ-F-035 (which predates the SOURCE field).
RATIONALE: Split from REQ-F-035 (issue #14, second pass). One of REQ-F-035's two cross-cutting invariants, given its own requirement rather than restated in each of the nine reads (REQ-F-059 to REQ-F-067 cite it) or folded into the agreement count (REQ-F-069): it constrains every read's own report as much as the count, it has to hold at every layer a reading passes through and is tested at each — the feed leaves a failed ticker ABSENT (TS-FEED-010, TS-FEED-014), the parse yields nothing rather than a zero (TS-YAHOO-001, TS-YAHOO-002), every read reports UNKNOWN and the count ignores it (TS-CONF-003, TS-INV-007), the model's evidence omits a "0 of 0" (TS-DEC-010) and the cockpit states them (TS-COCKPIT-001) — and REQ-F-038's absent-is-not-zero display rule cites exactly this obligation. TS-CONF-002 asserts the same per read but deliberately does NOT carry this id: StrictDoc honours only ONE `@relation` marker per test function (measured with 0.30.1 — a second marker silently drops the first) and that one line is already at the 100-column limit with the six ids it verifies more uniquely; TS-CONF-003's all-UNKNOWN case states the same fact through the count.
PRIORITY: must
STATUS: verified
ACCEPTANCE_CRITERIA: Traced to DES-DOM-CONFLUENCE, DES-DOM-YAHOOPARSE and DES-UI-COCKPIT and TS-CONF-003, TS-INV-007, TS-COCKPIT-001, TS-DEC-010, TS-FEED-010, TS-FEED-014, TS-YAHOO-001 and TS-YAHOO-002, passing, with 0 hard gaps.
ISSUE: GitHub issue #14 (REQ-F-035 atomic decomposition, second pass); see process/requirements-schema-upgrade.md.

[REQUIREMENT]
UID: REQ-F-069
VERIFICATION: T
TITLE: The agreement count — shown, given to the model, and gating the bot
STATEMENT: >>>
Prediction shall rest on AGREEMENT BETWEEN INDEPENDENT reads rather than on a stack of indicators derived from the same closes: an oscillator, a moving-average cross and a momentum study computed from one price series are one piece of evidence wearing three hats. The app shall therefore fetch and report reads that are independent of its own price history, each from a source it can actually obtain (REQ-F-059 to REQ-F-067). The count of agreeing reads shall be shown per instrument alongside the app's other signals, shall be given to the model as evidence in those words, and shall gate the bot: an index position shall not be opened while fewer than a configured number of the MEASURED reads agree with its side. That threshold shall be configurable, shall be satisfiable (never more than the number of reads actually available), and shall be able to be switched off — with the reads still shown and still given to the model, because a read nobody acts on is still information a reader is owed.
<<<
SOURCE: Design decision carried over from REQ-F-035. The implemented bar — a MAJORITY of the measured reads, floored at the configured number and clamped to what was measured — answers a measured regression: a fixed floor of 3 was a majority of five reads and a minority of nine, so every read added silently weakened the gate. REQ-F-035's SOURCE credits TS-PAPER-025 with documenting it; checked on 2026-09-29, the assertions that pin it (four of nine refused as needing five, five of nine taken) are in TS-PAPER-027.
RATIONALE: Split from REQ-F-035 (issue #14, second pass): the split plan's "majority-agreement gate". The display, model-evidence and gate halves stay in ONE requirement because REQ-F-035 states them as three uses of one number and requires the first two to survive the third being switched off. The STATEMENT keeps REQ-F-035's own words — "fewer than a configured number of the MEASURED reads" — and does NOT promote the implemented majority rule (`confluenceVerdict`: the larger of `minAgreeingReads` and a majority of the measured count, clamped to that count, 0 = off) to a stated obligation, because a split must not add obligations; the majority rule satisfies this requirement and is recorded in SOURCE, and making it normative is a separate change. Not a duplicate of REQ-F-036, whose majority-of-measured "agreement bar" grades the combined indication, not the bot's `no-confluence` refusal.
PRIORITY: must
STATUS: verified
ACCEPTANCE_CRITERIA: Traced to DES-DOM-CONFLUENCE and DES-UI-COCKPIT and TS-PAPER-027 (the `no-confluence` refusal names its numbers, a threshold above the measured count is clamped, four of nine agreeing is refused and five taken, 0 switches the gate off), TS-CONF-003 (the count per side), TS-DEC-010 (the count reaches the model's evidence in words) and TS-COCKPIT-001 (the count is shown beside what could not be measured), passing, with 0 hard gaps.
ISSUE: GitHub issue #14 (REQ-F-035 atomic decomposition, second pass); see process/requirements-schema-upgrade.md.

[REQUIREMENT]
UID: REQ-F-070
VERIFICATION: T
TITLE: Read inputs keyed the way their sources are keyed
STATEMENT: >>>
The reads shall be supplied from books that are keyed the way their sources are keyed, and a read shall never search the wrong one: the reference tickers are keyed by TICKER and the futures proxies by the app's own INSTRUMENT SYMBOL, and mixing them silently disables a read while leaving every test that mixes them in the same way green.
<<<
SOURCE: Measured defect: the futures-lead read looked for the futures proxy in the ticker book, was therefore permanently UNKNOWN in the running app, and its unit test passed because the test filed the futures in the same wrong book (regression TS-CONF-006); the same shape later left the cockpit's SPX500/NSDQ100 reference cards permanently empty in both front ends (regression TS-COCKPIT-011).
RATIONALE: Split from REQ-F-035 (issue #14, second pass). Its own requirement rather than folded into the two futures reads, because the rule is about the INPUT BUNDLE every read is computed from (`ReadInputs`/`readInputsFor`), and its consumers include the cockpit's reference cards, not only the read that happened to expose it first.
PRIORITY: must
STATUS: verified
ACCEPTANCE_CRITERIA: Traced to DES-DOM-CONFLUENCE and DES-UI-COCKPIT and TS-CONF-006 and TS-COCKPIT-011, passing, with 0 hard gaps.
ISSUE: GitHub issue #14 (REQ-F-035 atomic decomposition, second pass); see process/requirements-schema-upgrade.md.

[REQUIREMENT]
UID: REQ-F-071
VERIFICATION: T
TITLE: Each index read from its own constituent list, and the list named
STATEMENT: >>>
The constituent list shall be the one belonging to THAT index — up to ten names by weight, the Nasdaq-100's for a Nasdaq instrument and the S&P 500's otherwise — because the two lists agree at the top and differ exactly in the tail that distinguishes the indices, and reading the wrong tail reads a different market. The read shall name which list it counted.
<<<
SOURCE: Design decision carried over from REQ-F-035 (which predates the SOURCE field).
RATIONALE: Split from REQ-F-035 (issue #14, second pass). Its own requirement because three reads (REQ-F-064, REQ-F-065, REQ-F-066) and the constituent view (REQ-F-074) all count over this list; restating it in each would be four copies of one rule. "The read shall name which list it counted" is met by the participation read's detail ("… Nasdaq-100 heavyweights up") and by the constituent pulse's index name; the two volume reads, added to REQ-F-035 after that sentence was written, do not name the list in their own detail text — noted here, not claimed.
PRIORITY: must
STATUS: verified
ACCEPTANCE_CRITERIA: Traced to DES-DOM-CONFLUENCE and TS-CONF-001 (two ten-name lists, differing in the tail, each symbol selecting its own), TS-CONF-002 (one set of series gives each index its own answer, and the participation read names the index) and TS-CONF-004 (the two pulses read different names), passing, with 0 hard gaps.
ISSUE: GitHub issue #14 (REQ-F-035 atomic decomposition, second pass); see process/requirements-schema-upgrade.md.

[REQUIREMENT]
UID: REQ-F-072
VERIFICATION: T
TITLE: Volume bars aligned bar for bar — no volume means UNKNOWN, never zero
STATEMENT: >>>
The two volume reads (REQ-F-065, REQ-F-066) are what separate "the names are up" from "the names are being bought", and they require volume bars whose closes and volumes are ALIGNED bar for bar: a close series and a volume series parsed independently skip different empty minutes, and a VWAP computed across that shift is a number about nothing. Where a feed carries no volume — the volatility and yield indices do not — both reads shall be UNKNOWN rather than zero.
<<<
SOURCE: Design decision carried over from REQ-F-035 (which predates the SOURCE field).
RATIONALE: Split from REQ-F-035 (issue #14, second pass). Its own requirement rather than restated in both volume reads, because it is a DATA obligation on the parse (`yahooBars`, `VolumeSeries`) that both reads share, and it is verified at the parser (TS-YAHOO-006, TS-YAHOO-007) as well as at the reads (TS-CONF-005).
PRIORITY: must
STATUS: verified
ACCEPTANCE_CRITERIA: Traced to DES-DOM-YAHOOPARSE and DES-DOM-CONFLUENCE and TS-YAHOO-006, TS-YAHOO-007 and TS-CONF-005, passing, with 0 hard gaps.
ISSUE: GitHub issue #14 (REQ-F-035 atomic decomposition, second pass); see process/requirements-schema-upgrade.md.

[REQUIREMENT]
UID: REQ-F-073
VERIFICATION: T
TITLE: Volatility term structure — reported, a conviction damper, never a direction
STATEMENT: >>>
The volatility TERM STRUCTURE (the near leg against the far leg) shall additionally be reported, and shall never be counted as a direction: an inverted curve says the market is paying up for protection right now, which is a statement about how much the next print can overrule and not about which way it goes. It shall therefore only ever REDUCE conviction, exactly as an elevated level does.
<<<
SOURCE: Design decision carried over from REQ-F-035 (which predates the SOURCE field).
RATIONALE: Split from REQ-F-035 (issue #14, second pass). Its own requirement and NOT one of the nine reads: REQ-F-035 excludes it from the direction count explicitly, so folding it into the volatility-direction read (REQ-F-061) or the agreement count (REQ-F-069) would misfile it. Checked against REQ-F-036, which lets "the market regime (expected volatility and an imminent high-impact release)" only reduce the combined indication: overlapping in effect, NOT a duplicate — REQ-F-036 names the volatility LEVEL, not the term structure, and says nothing about reporting the near and far legs. The "only ever REDUCE" half is exercised by TS-LEAD-003 (an inversion cuts the combined indication, an unmeasurable term structure leaves it alone), which therefore now carries this requirement's tag beside REQ-F-036's.
PRIORITY: must
STATUS: verified
ACCEPTANCE_CRITERIA: Traced to DES-DOM-CONFLUENCE and DES-DOM-LEAD and TS-CONF-001 (both legs fetched), TS-CONF-006 (reported as inverted or normal and never as a direction, the thirty-day leg standing in for the three-month, UNKNOWN without the near leg) and TS-LEAD-003 (an inversion reduces conviction), passing, with 0 hard gaps.
ISSUE: GitHub issue #14 (REQ-F-035 atomic decomposition, second pass); see process/requirements-schema-upgrade.md.

[REQUIREMENT]
UID: REQ-F-074
VERIFICATION: T/I
TITLE: The index constituents in their own view — a stand-in for breadth, said on screen
STATEMENT: >>>
The constituents shall additionally be shown IN THEIR OWN VIEW as an early read on the two indices: the ten names of each index side by side with their session moves, how many of them are up, the average move of the readable ones, and which single name is leading and which is lagging — because an index carried by one name and an index carried by all ten are different situations that the same index price cannot tell apart. That view shall state, on screen rather than in a comment, that it is a STAND-IN for market breadth, and a constituent whose price could not be read shall be shown as UNKNOWN rather than as a zero move.
<<<
SOURCE: Design decision carried over from REQ-F-035 (which predates the SOURCE field).
RATIONALE: Split from REQ-F-035 (issue #14, second pass): a DISPLAY-only obligation. The split plan suspected both displays were "arguably REQ-F-038 territory"; checked against the STATEMENTs, NOT a duplicate of either candidate. REQ-F-038 governs the declarative second front end (the cockpit) and never mentions the index constituents — its absent-is-not-zero display rule cites the measurability rule (REQ-F-068), not this view. REQ-F-036's last paragraph requires a GRAPH of the heavyweights normalised to their own session open, showing every constituent and refreshed while open; this requires the per-name summary (session moves, count up, readable average, leader and laggard) and the on-screen stand-in caveat. Both live in the same Heavyweights window (DES-UI-HEAVY), which is why that design element satisfies both. The bot console's constituent bar chart (DES-CON-BOT) shows the same names under the same UNKNOWN-not-zero rule (TS-CON-002) but is not "their own view"; the on-screen caveat is the Heavyweights window's, checked from the outside by the Squish case `tst_heavyweights_early_read` (hence T/I: the C++ suite pins the summary, the GUI suite or an inspection the caveat).
PRIORITY: must
STATUS: verified
ACCEPTANCE_CRITERIA: Traced to DES-UI-HEAVY, DES-CON-BOT and DES-DOM-CONFLUENCE and TS-CONF-004 (rows, count up, readable-only average, leader and laggard, unread names UNKNOWN and never flat) and TS-CON-002 (an absent constituent dashed, never drawn as 0.00%), passing, plus the Squish case `tst_heavyweights_early_read` for the on-screen stand-in caveat, with 0 hard gaps.
ISSUE: GitHub issue #14 (REQ-F-035 atomic decomposition, second pass); see process/requirements-schema-upgrade.md.

[REQUIREMENT]
UID: REQ-F-075
VERIFICATION: T/I
TITLE: The cap-weighted constituent lead — one summarised direction, its approximate weights labelled
STATEMENT: >>>
Beside the equal-weight average, the app shall report a single SUMMARISED direction for the top constituents together — a CAP-WEIGHTED move, each name scaled by its share of the index and renormalised over the readable names — as the "in which direction are the top names pulling the index, up or down" indicator, because the index itself is cap-weighted and a large name moving is not a small name moving, and the top names can carry the index against the majority count (the index lagging its heaviest constituents is exactly the situation this is meant to surface). Direction shall be carried by a sign and a shape, never by colour alone. The weights used shall be an APPROXIMATE STATIC snapshot — this app does not fetch live index weightings — and shall be labelled as such on the same footing as the breadth stand-in caveat — enough to weight the heaviest name above the lightest by roughly the right ratio, never a claim to the index's exact construction.
<<<
SOURCE: Design decision carried over from REQ-F-035 (which predates the SOURCE field).
RATIONALE: Split from REQ-F-035 (issue #14, second pass): a DISPLAY-only obligation — the lead is shown, never fed into the decision math (the combined indication still reads the equal-weight average). NOT a duplicate of REQ-F-036, whose indication is computed from "the index's own constituent field" without any cap weighting, nor of REQ-F-038, which never mentions the constituents. At the split (2026-09-29) STATUS was `approved`, not `implemented`: the cap-weighted computation, its disagreement with the count, the ▲/▼-plus-sign indicator, the console's one-line layout and the gauge's signed, proportional, clamped bar were implemented and tested (TS-CONF-007, TS-CON-006, TS-GAUGE-001), but the weights were labelled as an approximate static snapshot only in source comments. One domain label, `capWeightsNote()` ("approx. static weights"), is now shown wherever the lead is: the pulse headline ("cap-wt +0.42% (approx. static weights)"), the end of the console's Top-10 lead line, and the Heavyweights window's gauge heading.
PRIORITY: must
STATUS: verified
ACCEPTANCE_CRITERIA: Traced to DES-UI-LEADGAUGE, DES-CON-BOT and DES-DOM-CONFLUENCE and TS-CONF-007, TS-CON-006 and TS-GAUGE-001, passing, with 0 hard gaps: the static-weights label is pinned in the headline (TS-CONF-007) and on the console line (TS-CON-006); the gauge heading uses the same `capWeightsNote()` (inspection).
ISSUE: GitHub issue #14 (REQ-F-035 atomic decomposition, second pass); see process/requirements-schema-upgrade.md.

[REQUIREMENT]
UID: REQ-F-076
VERIFICATION: T/I
TITLE: Live execution of the bot's SPX500/NSDQ100 decisions under an explicit double-pressed, time-bounded arming with hard caps
STATEMENT: >>>
The bot's decisions for a FIXED scope — SPX500 and NSDQ100, and no other instrument — may be mirrored to real orders, but ONLY while a human has armed real-money execution by the REQ-N-005 double press on a control that names the whole grant: the scope, the per-order cap, the daily-loss cap and the duration. Nothing the app computes shall arm it. Arming shall additionally require that the broker client is live (real credentials and mode "real") and that the kill switch is not tripped; a refused arming shall name which of those refused it. The REQ-F-031 readiness verdict is NOT a precondition of arming — an owner decision, 2026-09-30 — but an arming made while it is unmet shall say so in the log, naming every unmet threshold, so the person who armed did it in the face of the record rather than in ignorance of it. The arming is time-bounded (REQ-N-009's armed state, expiring on its own), is never persisted across a restart, and every order passes REQ-N-009's validated-armed-recorded path — the validator, the armed state with its caps and the append-only audit record — so no mirrored order can skip any of the three.

The per-order stake shall be the SMALLER of the configured cap and the paper trade's own stake, sent at the paper trade's leverage and with the paper trade's geometry: the stop-loss and take-profit AMOUNTS scale with the stake so the live position carries the same stop and target rates the simulated one does. At most ONE live position shall be held per instrument. A realised daily loss over the mirrored positions reaching the configured cap shall TRIP the kill switch — sticky, cleared only by an explicit human action — after which no further order is sent that day or any later one until it is cleared. A paper close of a mirrored trade shall close the live position; a live position whose broker id is not yet known shall be reported as needing a manual close rather than silently left open. Both caps shall be configuration with safe defaults (250 EUR per order, 250 EUR realised daily loss), and a cap of zero shall mean that no order can be sent, never that the cap is off.

The window shall show the armed state and its caps, the mirrored positions with their broker ids, and the REQ-F-031 readiness verdict BESIDE the arming control. The paper bot shall keep its own books unchanged — the simulated position opens and closes exactly as it would without the mirror, so the record REQ-F-031 measures stays the record of the strategy, not of the live fills.
<<<
SOURCE: Owner request 2026-09-30 ("a button to use real money for robot trading with SPX500 and NSDQ100"), with the answers to the three questions asked before implementation recorded in RATIONALE.
RATIONALE: The owner's answers were: caps of 250 EUR per order and 250 EUR realised daily loss; scope SPX500 and NSDQ100 only, at most one live position per instrument, leverage as the paper bot chose; and — the third — that the REQ-F-031 readiness verdict should NOT be a precondition of arming. That third answer is implemented as an owner decision taken IN REQ-F-031 itself (amended 2026-09-30, on the owner's explicit instruction after the first implementation had kept the gate): the readiness verdict is shown beside the control and logged at arming, but does not lock it. The safeguards that remain are the ones this requirement names — the caps, the two-instrument scope with one live position each, the sticky kill switch tripped by the daily loss, the audit record and the double-pressed, time-bounded arming — and RISK-005 carries the raised score. The project's own instructions used to name "the gate passing" as a condition for wiring live execution; that clause is superseded by this decision, and the change-management strategy's two independent approvals apply to it. The precedent for replacing a per-order double press with a double-pressed ARMING is REQ-F-028: an autonomous executor cannot present each order for confirmation, so the confirmation moves to the grant, and the grant names everything it permits. The mirror is GUI-only (the console front ends hold no gateway) and the paper runner itself still has no route to an order endpoint — it emits trade events, and the one object holding a gateway is composed in the main window.
PRIORITY: must
STATUS: implemented
ACCEPTANCE_CRITERIA: Traced to DES-DOM-LIVEMIRROR (the pure plan and day-loss rules; TS-LIVE-001..004), DES-UI-LIVEBOT (the executor over the guarded send; TS-LBOT-001..005), DES-SVC-GATEWAY (the real gateway refusing a non-live client; TS-GATE-007) and DES-SVC-CLIENT (a market order on a priced instrument that is not on screen, and the opened position id as a signal; TS-CLI-042), all passing with 0 hard gaps. Inspection: the bot window's "Real money" box shows the armed state, the caps, the mirrored positions and the readiness verdict beside the arming button, the arming button needs two presses within one second, and an arming made over an unmet readiness verdict succeeds but logs every unmet threshold (TS-LBOT-005).
ISSUE: none

[REQUIREMENT]
UID: REQ-N-008
VERIFICATION: T
TITLE: Money shall be counted, not approximated
STATEMENT: >>>
Every amount that can move real money — a stake, a stop-loss or take-profit amount, a fee, a per-order or per-day cap, a booked result — shall be represented as an INTEGER NUMBER OF MINOR UNITS of a named currency rather than as an unrestricted floating-point number. The reason is not elegance: 0.1 is not representable in binary, a sum of a hundred such amounts drifts, and a comparison against a cap can then answer "just under" for an amount that is actually over. An amount whose least significant digit is a rounding artefact must never be the thing a broker is asked to trade.

The type shall make the lossy step EXPLICIT and singular: conversion from a measured double (a rate, a percentage of equity, a volatility-derived stake) shall be a named operation that states its rounding, and everything downstream shall then be exact integer arithmetic. Amounts of different currencies shall not silently combine — the app deals in EUR display and a USD account currency, and an addition that ignores that difference is a defect the compiler currently cannot see. An operation on mixed currencies shall therefore yield an amount that reports itself INVALID rather than a plausible wrong number, and an invalid amount shall never be sent anywhere.

Rounding shall be defined rather than inherited: conversion shall round half away from zero, and scaling an amount by a fraction shall do the same, so a stake computed as a fraction of equity is reproducible across platforms and across runs. The type shall be a value type, comparable and printable, cheap enough to be used everywhere the money words appear, and its arithmetic shall be tested for the cases that actually break naive money code: repeated accumulation, a cap comparison at the boundary, negative amounts (a credit is money too), and the mixed-currency refusal.
<<<

[REQUIREMENT]
UID: REQ-N-009
VERIFICATION: T/I
TITLE: The live-order path shall be validated, armed, swappable and recorded
STATEMENT: >>>
The double-press gate of REQ-N-005 keeps a human in the loop for one action. It does not, on its own, make the request that leaves the machine CORRECT, nor does it leave a record of what was sent. Four things shall therefore stand between a decision and a real order, and each shall be a separate, separately testable piece.

First, VALIDATION. Every money-moving request shall pass a pure validator before it can be sent, and the validator shall refuse rather than repair: non-finite or non-positive amounts, an amount that is not an integral number of minor units, a leverage the instrument does not offer (the ladder, not a range), an unknown or unresolved instrument id, a units count above the instrument's own per-order maximum, a stop-loss or take-profit on the wrong side of the entry, a trigger rate on the wrong side for the order's direction, and an order currency that is not the ACCOUNT's currency shall each be a named refusal. Each refusal shall carry a STABLE machine-readable code alongside its human sentence, because a refusal that can only be read by a person cannot be counted, and a count is what tells a maintainer which check is actually firing.

Second, ARMING. Live execution shall require an explicit, visible, time-bounded ARMED state that the user enters deliberately and that nothing the app computes can enter on its behalf. The armed state shall carry the caps under which it was granted — a maximum per order and a maximum per day, both as REQ-N-008 amounts — and shall expire on its own so that an armed session cannot outlive the attention that granted it. It shall additionally provide a KILL SWITCH: one action that disarms immediately, is STICKY (it stays tripped until explicitly cleared, so a panic action cannot be undone by the next timer tick), and is honoured by every path that could send an order. While not armed, or while tripped, an order request shall be refused with the reason, and the refusal shall be indistinguishable in effect from having no credentials at all.

Third, a SEAM. Order placement shall go through an interface rather than directly to the broker client, and at least two implementations shall exist: the real one, and a fake that records exactly what it was asked to do and answers with a configured outcome. Without that seam the order path can only be tested against a live account, which means it is not tested. The fake shall be what the automated suite uses, and the choice of implementation shall never depend on a build flag that could differ between the tested and the shipped binary.

Fourth, an AUDIT RECORD. Every attempt — accepted, refused by validation, refused by the arming state, or rejected by the broker — shall be appended to a durable record carrying the request's complete fingerprint (instrument, side, amount, leverage, stop/target, order and account currency), the time the decision was made, the time it was sent, the request id used, and the broker's own answer verbatim where there was one. The record shall be append-only and shall survive a restart, because the question it answers ("what exactly did this machine send, and what came back") is asked after something has gone wrong, when memory and log scrollback are both gone.

Wiring these four to a real account remains a separate, deliberate act: this requirement specifies the machinery and its guarantees, and REQ-N-005 continues to govern the human confirmation at the moment of sending.
<<<

[REQUIREMENT]
UID: REQ-F-036
VERIFICATION: T/A
TITLE: One combined indication, and the constituent field it is read from
STATEMENT: >>>
The independent reads (REQ-F-059 to REQ-F-067) shall be combined into ONE indication per index instrument, so that the question a leveraged trade actually asks — is there enough agreement right now to justify size — has a single answer rather than nine partial ones a reader has to weigh in their head. That indication shall be computed from those independent reads (nine at the time of writing), the index's own constituent field, the session phase and the market regime (expected volatility and an imminent high-impact release), and shall report a side, a strength, a grade in words, and the leverage the EVIDENCE justifies. The count is deliberately NOT restated as a fixed number in the thresholds: the grade boundaries and the agreement bar are a MAJORITY of whatever was measured, so adding a read raises the bar instead of silently weakening it.

Three properties shall hold, and they are what makes the number worth having rather than a comforting aggregate:

An input that could not be MEASURED shall contribute nothing — never a zero, never a neutral guess — and the count of unmeasurable inputs shall be reported alongside the strength. The strength shall additionally be CAPPED by how much was measurable, so that half the inputs missing means at most half the strength whatever the available ones say: a strong-looking read built from two feeds must be impossible to mistake for one built from six. And the leverage the indication names shall be an UPPER BOUND from the evidence only — the per-trade risk budget, the correlation-bucket cap and the instrument's own offered ladder shall all still apply, and the smallest of them shall win. The indication shall never raise a limit; it may only lower one.

The session phase and the regime shall be able to REDUCE the strength and never to raise it: an opening that has not formed its range, a policy window, an imminent release or an elevated volatility index all mean that the next print can overrule whatever structure exists now, and a system that sized up into them would be reading its own confidence rather than the market.

The constituent field shall additionally be shown as a GRAPH of the index's own heavyweights over the session, each normalised to its own opening price so that instruments trading at different price levels can be compared on one axis. The graph shall show EVERY one of those constituents rather than only the ones that moved — a chart that dropped the quiet names would answer "who moved" instead of "are they moving together", and the second question is the one that leads the index. While that view is open it shall refresh at the resolution of the data behind it and state when it last did so; while it is closed it shall cost nothing.
<<<

[REQUIREMENT]
UID: REQ-F-037
VERIFICATION: T
TITLE: A probability shall be measured, not asserted — the prediction ledger
STATEMENT: >>>
The combined indication of REQ-F-036 reports EVIDENCE on a 0..100 scale. It shall never be presented as a probability, and no percentage shall be printed for the question a trader actually asks — "how likely is this instrument to be higher in five, fifteen, sixty or a hundred and eighty minutes" — unless that number was MEASURED. A probability is a claim about frequency; a weighted sum of indicators is not, and putting a percent sign on one would be the most dishonest thing this application could do.

The app shall therefore keep a PREDICTION LEDGER, and it shall record EVERY evaluation rather than every trade. A record of the positions actually opened can only measure the gate in front of the signal: it cannot see the calls that were right and skipped, and it inherits every bias of the rules that filtered it. Each row shall carry the time, the instrument, the side (or the fact that it stayed out, with the stable refusal code that decided it), the strength, HOW MUCH was measurable behind that strength, the mark the call was made at, the market regime it was made in, and whether a position was actually opened.

Outcomes shall be resolved from the ledger's OWN later rows for the same instrument, so that measuring what happened next needs no second store that could disagree with it. A pairing that is too far past the horizon asked about shall be REFUSED rather than stretched: resolving a five-minute call against the next session's first row would manufacture a result out of an overnight gap. The earliest qualifying row shall be used, since taking the latest available would silently lengthen every horizon as the record grows.

The reported probability shall be the measured hit rate of COMPARABLE calls — the same strength band, the same horizon — and until a band holds enough resolved samples the app shall say UNCALIBRATED and offer no number at all, naming how many samples it has and how many it needs. This is the discipline the live-money gate already follows: report the unmet threshold, never a placeholder. The expected RANGE over each horizon shall be reported even while the direction is uncalibrated, because how far an instrument can move is a property of its own bars rather than a claim about which way it will go.

Every score shall be reported beside BASELINES computed on exactly the same resolved samples: always-long, the previous five minutes' direction, and the side of the session VWAP. A directional hit rate without them is a boast — 58% is worthless if always-long scored 61% over the same minutes. A baseline that could NOT be measured shall be named as unmeasurable and excluded from the comparison, never scored as zero and thereby counted as beaten, and a claim to beat "every baseline" shall require that at least one of them was actually measured. The app shall also report a Brier score against the 0.25 that answering "50%, always" would earn, and shall state plainly when its own calls do not beat the baselines.

The regime label shall be measured or UNKNOWN, never guessed, and its precedence shall be explicit: a scheduled release outranks a volatility reading, which outranks the trend-versus-range question, because at that width the horizon's own noise swamps either answer.
<<<

[REQUIREMENT]
UID: REQ-F-038
VERIFICATION: T/A
TITLE: A second, declarative front end over the same tested logic — read-only by construction
STATEMENT: >>>
The application shall offer a second presentation of its evidence, built declaratively, over the SAME domain and service layers the existing desktop interface uses — not a reimplementation. The point is to demonstrate that the layering is real: if a second front end can be built without touching the domain, the domain was genuinely independent of its presentation, and if it cannot, the claim was decoration.

That second front end SHALL BE ABLE TO TRADE, and every safeguard that stands in front of the existing interface's order path shall stand in front of it too — SHARED, not reimplemented. This supersedes the earlier read-only clause, which was a scoping decision recorded as though it were a safety property; the safety property is the SAFEGUARD, not the absence of the feature. Concretely: the double-press confirmation of REQ-N-005 shall gate opening and closing alike, and shall be the SAME implementation the existing interface uses, since a confirmation mechanism with two implementations is in practice the weaker of the two. The last pure check before an order is sent shall remain REQ-N-009's validator. The object able to reach an order endpoint shall remain a single one per process, and the view-model shall not be it: a view-model that can place an order cannot be exercised safely by a test.

The confirmation shall name the WHOLE order, not merely its side, so that an arming cannot be inherited by a different order — changing the amount, the leverage or the side shall disarm, and a confirmation of one position's close shall never close another. An arming shall expire, and a stale one shall re-arm rather than commit. Every arming shall be VISIBLE, because an arming nobody can see is indistinguishable from a control that did nothing. Where trading is impossible the view shall say WHY, most fundamental obstacle first, rather than presenting a control that silently does nothing.

Any claim the view makes about its own safety shall be true of the build making it: a banner asserting that no order can be placed shall not survive into a build where one can, since a safety statement that over-claims is worse than none because it is believed.

The data it presents shall be prepared by a SEPARATELY TESTABLE component rather than computed inside the declarative markup. What a view shows is a claim about the system, so it shall be verifiable by an automated test that does not require rendering: a screenshot proves that something was drawn, never that it was right. Every number the view displays shall therefore come from that component, and the component shall be tested directly.

Three display rules follow from requirements already stated elsewhere, and the view shall not be permitted to soften any of them. An input that could not be measured shall be shown AS unmeasurable and shall never be rendered as a zero or a neutral midpoint (REQ-F-068). A strength on the 0..100 evidence scale shall never be presented as a probability, and where a measured probability does not exist the view shall say UNCALIBRATED rather than print a number (REQ-F-037). And every quantity derived from a market feed shall carry its FRESHNESS: a value whose quote is stale shall be visibly distinguished from a live one, and a value that cannot be obtained shall be shown as absent rather than as its last known reading, because a dashboard that renders a stale price in the same style as a live one misleads silently and continuously.

Identity in that view shall not rest on colour alone. Where a state is encoded by colour it shall also be encoded by shape, glyph or text, so that the view remains readable without colour discrimination — the up/down convention of the domain is precisely the pair that red-green colour blindness cannot separate. That rule shall bind the PRICE CHART too, where the convention is strongest: an up bar and a down bar shall differ in FILL as well as in colour, and the chart shall draw few enough bars for that fill to be visible — a body reduced to the width of its own border carries no fill channel at all, so a chart that shows a whole session at one-minute resolution has silently voided the guarantee while still claiming it. Where the view therefore shows only part of the series it shall SAY which part.

That second front end may be delivered as its own executable where a technical constraint requires it, provided it is built over the SAME domain, service and view-model components and adds no logic of its own. One such constraint is present and shall not be worked around by duplicating code: the charting module that supplies the candlestick view declares many class names identically to the charting module the existing interface uses, so a single binary linking both cannot resolve either, and the failure is silent — the declarative view renders empty with no error. Where a component of the view is unavailable in a given process, the view shall degrade to a STATED reason and shall not take the rest of the presentation down with it, since an empty panel reads as "no data", which is a different and false claim.

The bars that chart draws shall be assembled by the separately testable component above, under the same absent-is-not-zero discipline as every other reading: a bar shall be drawn only when all four of its values are present and mutually consistent, an incomplete or contradictory bar shall be discarded whole rather than repaired into shape — repairing invents an extreme the market never printed, and one invented extreme moves the entire scale — and the vertical scale shall cover the extremes actually reached rather than the opening and closing levels, which would cut those extremes off at the frame.
<<<

[REQUIREMENT]
UID: REQ-F-039
VERIFICATION: T
TITLE: Crowd sentiment and positioning data foundation
STATEMENT: >>>
The application shall be able to collect, normalize and store timestamped crowd-positioning, options, volatility, institutional-positioning, social and macro observations for its index instruments, as the FOUNDATION a later transparent crowd score and an offline-trained probability model rest on. This requirement is the data layer ONLY: no machine-learning model, no real-money execution and no directional trade follows from it — every downstream proposal remains paper or advisory and gated by the deterministic risk rules that already exist.

Each observation shall be a NORMALIZED, immutable record carrying its instrument, the family it belongs to, the concrete provider that produced it, a source-specific series identifier, its value and unit, its schema version, and — decisively — TWO timestamps in UTC: the time the datum is ABOUT (its event time) and the time it became KNOWN (its received or publication time). The two shall be kept distinct and both stored, because a datum published after the period it describes — the weekly Commitments-of-Traders report describes a Tuesday but publishes the following Friday — must never be treated as known before it was; that is the single most important guard against a model that appears to predict the past. A record that could not be measured shall be marked NOT VALID and shall never be read as a zero, and its freshness shall be reported as live, stale or absent against a configured threshold, with absent remaining distinct from stale.

Data shall be obtained through a provider SEAM: an interface with a mock — and, later, a recorded-fixture — implementation, so the whole subsystem builds, runs and is tested WITHOUT any paid subscription or network, and a missing credential shall be a recoverable "unavailable" state rather than a failure. The initial, licence-safe providers shall be the free public sources (the Commitments of Traders report and the Federal Reserve series including the volatility index); scraping shall not be used where no public API is offered, and no downloaded commercial dataset, credential or personal datum shall be committed. When a real provider is added its network access shall be asynchronous and shall never block the interface thread.

Persistence shall keep the RAW observations separate from the features, labels, predictions and realized outcomes that later phases derive from them — never one oversized table — with a unique identity per datum (provider, series, instrument, event time) so that re-fetching the same observation is idempotent rather than a duplicate, and shall carry a schema version so it can be migrated deliberately.
<<<

[REQUIREMENT]
UID: REQ-F-040
VERIFICATION: T
TITLE: Transparent rule-based crowd score
STATEMENT: >>>
The application shall compute a TRANSPARENT, rule-based crowd score for its index instruments from the normalized observations of REQ-F-039 — a number a person can read and reproduce, deliberately NOT a machine-learned model — so that it can serve as the BASELINE any later trained model must demonstrably beat. The score shall be evidence only: it shall not place a trade, and any proposal derived from it shall remain paper or advisory and gated by the deterministic risk rules that already exist.

The score shall combine four component families — retail positioning, options and volatility, institutional positioning, and social and news — each first NORMALIZED against its own PAST history (a z-score computed only from values that preceded it, so a component carries no look-ahead), then combined by CONFIGURABLE weights whose defaults are stated as HYPOTHESES rather than proven rules. The sign convention of every component shall be documented, and the retail component shall be treated as CONTRARIAN — a crowd that is heavily long is a bearish input.

Missing data shall never be treated as zero: a component that could not be measured — absent, or with too little history to normalize — shall be EXCLUDED from the score with the remaining weights renormalized, NAMED in the result, and shall lower both the reported DATA COVERAGE and the CONFIDENCE. Source freshness shall enter the confidence, so a stale component counts for less than a live one. The result shall report, alongside the score and its direction in words, the coverage, the confidence, the per-component CONTRIBUTIONS, the age of the newest and oldest input, the warnings, and a calculation VERSION; and the score together with a snapshot of its inputs shall be persisted in a store layer SEPARATE from the raw observations, for later auditing.

A Qt view-model shall expose the score for presentation WITHOUT computing any of it, so the number a view shows is the number the rule produced. It shall be usable with mock data and shall carry direction and freshness by words, not by colour alone.
<<<

[REQUIREMENT]
UID: REQ-F-041
VERIFICATION: T
TITLE: Offline training pipeline for the crowd model
STATEMENT: >>>
The crowd subsystem's trained model shall come from an OFFLINE training pipeline that is a development-time tool and NEVER a runtime dependency: the application shall build, run and pass its tests with none of the pipeline's libraries installed, and nothing the pipeline produces shall place a trade — a trained model remains paper or advisory evidence behind the deterministic risk rules that already exist.

The pipeline shall assemble its dataset from the SAME raw observation store the application writes (REQ-F-039), joining every observation to a decision time AS OF ITS RECEIVED TIME: a datum enters a row only when its received (publication) time is at or before the row's decision time, so a publication-lagged datum — the Commitments-of-Traders report is about a Tuesday but released the Friday after — can never inform a decision dated before its release. A missing datum shall stay missing (a named absence with a measured/not-measured marker), never a zero; per-series normalization shall be computed only from values received BEFORE the datum it normalizes; and the dataset shall carry a stable, versioned feature manifest whose names are append-only, so the trainer, the exported model and any later consumer agree on columns BY NAME rather than by position.

Labels shall be three classes — LONG, NO_TRADE and SHORT — derived from the instrument's FORWARD return over a configurable horizon with a DEAD ZONE representing the round-trip cost of taking the trade: a move that would not clear its own cost labels NO_TRADE, so that "do not trade" is learned as an outcome rather than treated as a failure; and a row whose horizon runs past the available price history shall be DROPPED, never labelled by invention.

Validation shall be PURGED WALK-FORWARD: a model is evaluated only on data strictly later than everything it trained on, and a training row whose LABEL WINDOW reaches into the evaluation block — extended by a configurable embargo — is PURGED, because forward-return labels overlap in time and a random split would let the model see the future and report a fiction. Every reported result shall sit beside NAMED BASELINES computed on the identical evaluation rows — at least the majority class and the transparent crowd score of REQ-F-040 — so "the model beats the baseline" is a measured claim, never an impression.

The trained baseline models (a logistic regression and a gradient-boosted-trees classifier) shall be exported to the ONNX exchange format carrying, as embedded metadata, the feature names in order, the imputation values a consumer must apply, the class order and the manifest version; and the exported artifact shall be verified to reproduce the trained model's own probabilities before it is kept — an export that disagrees with its source shall be deleted and reported, never shipped. The dataset build, labelling and split logic shall run on the Python standard library alone, so the leakage and labelling rules are testable on every machine the project supports; the fitting and export step may require the optional, setup-provisioned environment and shall REFUSE with the project's "skipped" exit code — writing nothing — when that environment is absent, when the dataset is too small, or when the labels hold fewer than two classes, rather than emit a model that means nothing.
<<<

[REQUIREMENT]
UID: REQ-F-042
VERIFICATION: T
TITLE: Optional in-process inference for the trained crowd model
STATEMENT: >>>
The application shall be able to LOAD and RUN a crowd model exported by the offline pipeline (REQ-F-041) in-process, behind a SEAM — one interface with a test double — so that everything consuming a prediction is testable without the real runtime, mirroring the provider seam of REQ-F-039.

The inference runtime shall be OPTIONAL AT BUILD TIME: on a machine without it the application shall configure, build, run and pass its tests identically, with the capability reporting itself UNAVAILABLE in words that name the remedy — never a build failure, never a crash, and never a silently absent feature a reader could mistake for a broken one. The runtime shall be provisioned by the same optional setup mode as the training environment, and no machine-specific path shall be committed.

The model file's own EMBEDDED metadata shall drive the inference, so the trainer and the consumer cannot drift apart silently: input features shall be matched BY NAME against the metadata's ordered feature list, a missing or non-finite input shall be imputed with the EXACT value the trainer embedded for that feature — with the number of imputed features REPORTED alongside the answer, because a prediction made mostly of fill-ins is a weaker claim — and the class labels of the answered probabilities shall come from the metadata, never from an assumption about column order. A model whose metadata is absent, unparsable or inconsistent — imputation values not matching the feature list, no classes — shall be REFUSED with a stated reason rather than scored.

Every failure shall be recoverable and named: a missing file, an unreadable graph, and a runtime error during scoring shall each produce an error result while the application carries on. An answer that does not form a probability distribution over the stated classes shall be refused rather than repaired.

The output is EVIDENCE ONLY: this requirement wires no prediction to any trading decision. Any later consumer remains paper or advisory behind the deterministic risk rules that already exist, and the probabilities remain subject to the measurement discipline of REQ-F-037 before anyone treats them as calibrated.
<<<

[REQUIREMENT]
UID: REQ-F-047
VERIFICATION: T
TITLE: One-shot instrument advice on the console
STATEMENT: >>>
The application shall offer a CONSOLE program that, given one instrument symbol, gathers the SAME evidence the interactive application reasons from — the technical ensemble, the web rating, the news headlines with their sentiment, the volatility and calendar regime, the crowd sentiment, the independent intraday series, the reference-series reads where the instrument has them, the costed trade plan, the persisted crowd score with the optional in-process model's labelled prediction, and the optional local model's pick — and prints ONE verdict with its reasons: a proposal (side, leverage, stop, target, stake suggestion) or a reasoned "no trade", followed by what every source said, with an ABSENT source named as absent rather than silently omitted or zeroed.

The program is ADVISORY BY CONSTRUCTION: it shall link no order path, so no invocation of it can place, size or cancel anything, and its output shall say so. It shall be scriptable: distinct exit codes for "proposal", "no trade" and "could not gather enough data", a bounded gathering time, and a machine-readable variant of the verdict on request. The verdict-and-reasons text shall be built by a component testable WITHOUT any network or terminal, so every line it can print is pinned headless — the same discipline as the bot console's view.

The program shall optionally KEEP RUNNING and re-report on a configurable interval, and for an INDEX it shall include that index's top-ten constituents' live session moves each cycle (worst-first, an absent constituent dropped rather than shown as a flat zero). It shall also optionally run a SIMULATED paper-trading bot focused on that one instrument, on its OWN persisted book kept separate from any other bot's, trading the same decision the report shows and printing each open, close and refusal — paper money on live prices, with no order path, like every advisory feature here.
<<<

[REQUIREMENT]
UID: REQ-F-048
VERIFICATION: T
TITLE: Portfolio-aware buy proposals as a spreadsheet
STATEMENT: >>>
The application shall offer a CONSOLE program that reads the account's OWN portfolio and free cash, evaluates every catalogued instrument with the same evidence stack as the single-instrument advisor, and writes a ranked buy proposal as a spreadsheet file that Excel and LibreOffice open natively — four sheets: the ranked PROPOSAL (side, confidence, leverage, stop, target, an ADVISORY stake suggestion bounded by the cash that actually exists, the correlation bucket and any constraint that demoted the candidate), the per-candidate EVIDENCE, the PORTFOLIO itself with its per-bucket exposure, and a DATA HEALTH sheet naming every source that did not arrive.

Only candidates whose COSTED plan is actionable shall rank — a direction that cannot pay its own costs proposes nothing — and CONCENTRATION shall demote, not forbid: a candidate whose correlation bucket already holds a large share of the invested money moves down the ranking with the reason NAMED, because a dozen positions in one bucket are one bet. When the portfolio cannot be read the report shall rank over a flat book and SAY so, never pretend. The program is ADVISORY BY CONSTRUCTION (no order path linked, the disclaimer part of the file), and both the sheet builder and the spreadsheet writer shall be testable without a network, a terminal or a spreadsheet application.
<<<

[REQUIREMENT]
UID: REQ-F-043
VERIFICATION: T
TITLE: Crowd & AI dashboard with a collection loop
STATEMENT: >>>
The application shall RUN the crowd subsystem it has so far only built and tested: a COLLECTION LOOP that periodically asks every CONFIGURED provider for the focus instruments, persists the observations into the raw store — idempotently, so a repeated fetch can never grow the record — recomputes and persists the transparent crowd score of REQ-F-040, and, when an exported model is present, scores it in-process through the optional inference seam of REQ-F-042. An unconfigured provider shall be shown as UNAVAILABLE in words and asked nothing; a provider failure shall become a named status beside the others, never a crash and never invented data.

A DASHBOARD view shall present what the subsystem knows, honestly: per-provider state in words (configured, unavailable, or the last issue), the crowd score with its direction in words, confidence, coverage, per-family contributions and warnings — missing families NAMED, never zeroed — and the model verdict: its availability and readiness in words, and when it scores, the class probabilities LABELLED from the model's own embedded metadata beside the COUNT of imputed inputs, because a prediction made mostly of fill-ins is a weaker claim than one made of measurements. Model inputs the collector cannot compute in-process — the price-context features — shall be left MISSING for the model's own embedded imputation and counted as such, never fabricated in a second implementation that could drift from the trainer's.

The dashboard is EVIDENCE ONLY: it shall state that the signals are experimental and not financial advice, it shall offer no trading affordance, and nothing in the loop or the view shall reach an order path — the deterministic risk rules and the double-press gate remain the only route to a real order. Optional local-LLM EXPLANATIONS of the evidence — words only, never prices, probabilities, stops or sizing — remain DEFERRED within this phase until they can be built with their own tests.
<<<

[REQUIREMENT]
UID: REQ-F-044
VERIFICATION: T
TITLE: Local text-sentiment features for the social family
STATEMENT: >>>
The application shall be able to turn the news HEADLINES it already fetches into the crowd subsystem's SOCIAL-family observations using a LOCAL text-sentiment classifier — a financial-domain BERT model exported to the ONNX format — so that the fourth family of the crowd score and of the training dataset can run on measured data without any social-network API, key, or scraping.

The capability shall be DOUBLY OPTIONAL: it requires the build-time inference runtime of REQ-F-042 AND a model directory the user provisions with the offline exporter tool — under the model's OWN licence terms, which the tool shall name rather than accept silently. Absent either, the feature shall report itself unavailable in words and nothing else changes: the headlines keep flowing to the panels that already show them, and no sentiment is invented.

Text shall be encoded with the model's OWN vocabulary, faithfully: WordPiece tokenization with greedy longest-match subwords, unknown words mapped to the unknown token, the classifier's framing tokens, and truncation at a stated maximum — a tokenizer mismatched to its model scores noise with confidence, which is worse than scoring nothing. The meaning of the answered classes shall come from a labels file exported BESIDE the model, never from an assumed column order, and a label set that does not name positive and negative shall be REFUSED.

The published sentiment shall be the NET (probability of positive minus probability of negative) over the scored headlines, stored as a NORMAL observation of the social family — event time quantized to the hour so the idempotent store is not flooded by every news poll — and entering the score, the dataset and the model features by the same rules as every other series. Failures shall be recoverable and named: a missing model directory, a malformed vocabulary, a label set without meaning, an empty headline set and a runtime error mid-score shall each produce an unavailable state or an error result while the application carries on. The output is EVIDENCE ONLY, with no route to an order.
<<<

[REQUIREMENT]
UID: REQ-F-045
VERIFICATION: T
TITLE: Local-LLM explanation of the crowd evidence, words only
STATEMENT: >>>
The crowd dashboard shall be able to ask the OPTIONAL local model (the REQ-F-030 machinery — no cloud, no key) to EXPLAIN the evidence it currently shows, in plain words a person can read beside the numbers. The request shall carry the SAME evidence the view presents, so the words are about what the user sees and nothing hidden.

The explanation is WORDS ONLY, enforced by construction rather than by trust: the answered text shall be DISPLAYED and consumed by NOTHING — no parser reads numbers out of it, no decision path receives it, and the view shall label it as the words of a small local model whose numbers are not data. The model shall be instructed to give no prices, targets, sizes, stops, probabilities or buy/sell instructions, but the safety property is the wiring, not the instruction.

Without a configured model the feature shall report itself unavailable in the established words; a transport failure, an empty answer and an unreadable answer shall each be a NAMED error result, never a blank that reads as "nothing to say". The parse shall be defensive in the way the proposal parse already is — a small model's JSON is approximate, and for prose the honest fallback is the prose itself — and one request shall be in flight at a time, sharing the advisor's existing discipline.
<<<

[REQUIREMENT]
UID: REQ-F-046
VERIFICATION: T
TITLE: Crowd evidence reaches the paper bot, as evidence only
STATEMENT: >>>
The crowd subsystem's findings shall be able to reach the paper bot's decision model as EVIDENCE LINES beside the technical evidence it already reads: per focus instrument, the transparent score's own headline and — when the in-process model has answered — its probabilities LABELLED from the model's embedded metadata, marked EXPERIMENTAL and UNCALIBRATED with the imputation count stated, because a probability is measured, never asserted (REQ-F-037).

The line shall GATE, SIZE and STOP nothing: no refusal code, no sizing rule, no exit rule and no risk cap reads it — it informs the model exactly like every other evidence line, and the deterministic risk rules remain the only governor of what the bot may do. Nothing measured shall mean NO line — absent evidence must never appear as a neutral-looking zero — and clearing an instrument's line shall remove it rather than leave a stale claim in every later prompt. The input is OPTIONAL: a front end without the collection loop passes nothing and behaves identically.
<<<

[[/SECTION]]

[[SECTION]]
TITLE: Non-functional requirements

[REQUIREMENT]
UID: REQ-N-001
VERIFICATION: A/I
TITLE: Cross-platform build (desktop + mobile + ARM64 single-board)
STATEMENT: >>>
The app shall build and run on Linux and Windows desktops with Qt ≥ 6.5, and shall be buildable for Android (APK via androiddeployqt, provisioned by setup.sh/setup.ps1 android and built by tools/build_android.{sh,ps1} for both arm64-v8a and x86_64, with the INTERNET permission the REST client needs) and iOS from the same CMake project. The Android APK shall be verified by building it; the emulator run is a manual step, since it needs a hypervisor the build machine may not expose.

Linux support shall cover ARM64 (aarch64) as well as x86-64, so the app runs on a Raspberry Pi 4/5 or Zero 2 W with a 64-bit Raspberry Pi OS Trixie (Debian 13) or newer — the OS floor is not a choice but a measured consequence: Qt's official aarch64 binaries require GLIBC_2.38 (libQt6Gui, libQt6Network; verified across Qt 6.8.3, 6.9.3 and 6.11.1), which Bookworm's glibc 2.36 does not provide, and Bookworm's own Qt 6.4.2 is below the Qt floor above. The host architecture shall be DERIVED, never assumed: setup.sh shall provision Qt's official Linux ARM64 kit (aqt host linux_arm64, arch linux_gcc_arm64, installed as ~/Qt/$QT_VERSION/gcc_arm64) and every Linux entry point shall resolve that kit itself (tools/common.sh), so no Raspberry Pi user has to pass QT_PREFIX by hand; where no ~/Qt kit exists for the architecture the build shall fall back to the distribution's Qt 6 rather than fail. tools/package_appimage.sh shall produce an aarch64 AppImage from the same script that produces the x86-64 one. A 32-bit ARM userland is explicitly out of scope: Qt publishes no desktop binaries for it and Raspberry Pi OS 32-bit ships Qt 6.4, below the floor above.

Pipeline stages whose tools exist only for x86-64 or only under a license — the Axivion analysis above all — shall report `skipped` on ARM64 with the reason named, never fail; and the stages that need a specific compiler version (MC/DC coverage, ThreadSanitizer: clang ≥ 18) shall resolve the version present on the host instead of hardcoding it, since a Debian or Raspberry Pi OS release ships exactly one clang. The ARM64 Linux build and test run shall be verified in CI on an ARM64 runner (the build-linux-arm64 job), because the reference development machine is x86-64.
<<<

[REQUIREMENT]
UID: REQ-N-002
VERIFICATION: A/T
TITLE: Pure domain layer, linker-enforced layering
STATEMENT: The domain layer shall be pure (Qt Core only, no I/O, no UI); layering (ui → services → domain) shall be enforced by the linker.

[REQUIREMENT]
UID: REQ-N-003
VERIFICATION: T
TITLE: Resilient REST access
STATEMENT: 'REST access shall survive transient failures: idempotent GETs are retried on 429/5xx honouring Retry-After / RateLimit-Reset; non-GETs are never auto-retried.'

[REQUIREMENT]
UID: REQ-N-004
VERIFICATION: I/T
TITLE: No secrets in version control
STATEMENT: No secret (API key, user key) shall be stored in version control.

[REQUIREMENT]
UID: REQ-N-005
VERIFICATION: T/I
TITLE: Explicit confirmation for money-moving actions
STATEMENT: >>>
Money-moving actions shall require explicit user confirmation (double-press) and shall never be triggered by advisory features (plans, watchdog, AI). An autonomous executor (REQ-F-028's scripts, REQ-F-076's bot mirror) replaces the per-order double press with a double-pressed, visible, time-bounded ARMING that names the caps it is granted under; it is never armed by anything the app computes.
<<<

[REQUIREMENT]
UID: REQ-N-006
VERIFICATION: T/A
TITLE: GUI-thread responsiveness and measured hot paths
STATEMENT: 'Compute-heavy work (Monte-Carlo, trade-plan building) shall run off the GUI thread; the per-tick open-trades refresh shall be allocation-free (model/view, in-place dataChanged); the domain hot paths shall be covered by deterministic benchmarks (tst_benchmarks) and a profiling entry point (tools/profile.sh) with an optimized release build (./build_all.sh release) as the measuring target.'

[REQUIREMENT]
UID: REQ-N-007
VERIFICATION: T/A
TITLE: The GUI shall be testable, and a GUI test shall never reach real money
STATEMENT: >>>
Every widget a GUI test may need to address shall carry a STABLE objectName, and that shall be enforced rather than remembered: a checker shall report any member widget without one, and it shall run in the analysis stage. Text and position are not identification — wording changes with translation and position changes with layout, while an objectName only changes when someone renames the member, which the checker then reports. The object map of the GUI suite shall address widgets by objectName only.

A GUI test run shall be incapable of reaching a real broker account, and that incapacity shall be a property of the APPLICATION rather than of the test scripts: a single switch shall make the app answer "no credentials" at the one place every mode question reads, so there is no live mode, no broker network and no order path while it is set — whatever credentials are present on the machine. A switch respected only by the test scripts would stop working the first time someone ran the app by hand. The app shall state that forced mode in its own mode label, so a screenshot from a test run cannot be mistaken for a missing-credentials situation, and the switch shall not be settable to "off" by anything the app itself does. The GUI suite's first test case shall assert that mode from the outside, so a broken guarantee fails the suite before any test can act.

Licence-bound test tools shall never gate a build: a stage whose tool or licence is absent shall report that and skip (the project's "skipped" exit code), the pipeline shall stay green on its own checks, and the final quality report shall list which licences were missing — so a reader can tell "measured and clean" from "not measured here".
<<<

[[/SECTION]]
